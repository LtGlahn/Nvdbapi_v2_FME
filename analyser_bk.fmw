FME workspace analyser_bk.fmw

Parameters:
- SourceDataset_GEOPACKAGE = C:\DATA\leveranser\diverse\bruksklasse_differanser.gpkg   # GeoPackage File
- Avrunding = 1   # Antall siffer i lengeberegning km.X
- DestDataset_XLSXW = C:\DATA\leveranser\diverse\avvik_bruksklasse.xlsx   # Destination Microsoft Excel File

Readers:
- GEOPACKAGE_1: GEOPACKAGE from $(SourceDataset_GEOPACKAGE)

Writers:
- XLSXW_1: XLSXW to $(DestDataset_XLSXW)

Note: Spesial vs normal
bknorm_bkspesial_diff (reader GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
    -> delvisOverlapp [Tester_Input]
Note: Tømmer vs normal
bknorm_bktommer_diff (reader GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
    -> delvisOverlapp_2 [Tester_Input]
bkvinter_norm_spesial (reader GEOPACKAGE_1) [off]
    attributes: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
bkvinter_norm_tommer (reader GEOPACKAGE_1) [off]
    attributes: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
bruksklasse_norm_spesial (reader GEOPACKAGE_1) [off]
    attributes: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
bruksklasse_norm_tommer (reader GEOPACKAGE_1) [off]
    attributes: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
makstotvekt_kjt_skiltet_norm_tommer (reader GEOPACKAGE_1) [off]
    attributes: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
makstotvekt_vongtog_skilt_norm_tommer (reader GEOPACKAGE_1) [off]
    attributes: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
maksvogntoglengde_norm_spesial (reader GEOPACKAGE_1) [off]
    attributes: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
maksvogntoglengde_norm_tommer (reader GEOPACKAGE_1) [off]
    attributes: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
merknad_norm_spesial (reader GEOPACKAGE_1) [off]
    attributes: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
merknad_norm_tommer (reader GEOPACKAGE_1) [off]
    attributes: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
strekningsbeskr_norm_spesial (reader GEOPACKAGE_1) [off]
    attributes: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
strekningsbeskr_norm_tommer (reader GEOPACKAGE_1) [off]
    attributes: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

Bookmark: Spesialtransport
delvisOverlapp
    BKNORM_VEGREF = @Value(bknorm_vegref)
    VEGREF = @Value(vegref)
    PythonCaller_Output -> BulkAttributeRenamer
BulkAttributeRenamer
    ATTRCHOICE = All Attributes
    MODE_CHOICE = RENAME
    PATTERN_ACTION_DISP = ADDPREFIX
    REPLACE_STR = spesial_
    -> BulkAttributeRenamer_2
BulkAttributeRenamer_2
    ATTRCHOICE = All Attributes
    CASE_DISP = YES
    MODE_CHOICE = RENAME
    PATTERN_ACTION_DISP = STRINGREPLACE
    REPLACE_PATTERN = spesial_bknorm
    REPLACE_STR = bknorm
    -> AttributeCopier
    -> Tester_2
    -> Tester_3
    -> Tester_10
    -> Tester_11
AttributeCopier
    ATTR_TABLE:
      COPY bknorm_Bruksklasse > temp_bknorm
      COPY bknorm_Bruksklassevinter > temp_bknormvint
      COPY spesial_Bruksklasse > temp_bkspes
      COPY spesial_Bruksklassevinter > temp_bkspesvint
    -> Tester_7
Tester_10 [off]
    BOOL_OP = OR
    TEST_CLAUSE = TEST @Value(bknorm_Strekningsbeskrivelse) = @Value(spesial_Strekningsbeskrivelse)
    PASSED -> StatisticsCalculator_9
Note: Strekningsbeskrivelse normal - spesial
StatisticsCalculator_9
    COMPUTE_HISTOGRAM = NO
    GROUP_BY = bknorm_Strekningsbeskrivelse spesial_Strekningsbeskrivelse
    PREPEND_ATTR_NAME_CHOICE = For multiple results only
    STATS_ATTRS = spesial_lengde
    SUM_ATTR = lengde_sum
    SUMMARY -> ExpressionEvaluator_9
ExpressionEvaluator_9
    ACTION = Overwrite Existing Attributes
    ATTRLIST = lengde_sum
    EXPRESSION = @round(@Value(lengde_sum)/1000,$(Avrunding))
    -> Sorter_9
Sorter_9
    SORT_PARM = lengde_sum NUMERIC DESCENDING
    SORTED -> Strekningsbeskrivelse_normal_-_spesial_3
Strekningsbeskrivelse_normal_-_spesial_3: Inspector [off]

Bookmark: New Bookmark
Tester_2
    BOOL_OP = OR
    TEST_CLAUSE = TEST @Value(bknorm_Bruksklassevinter) = @Value(spesial_Bruksklassevinter)
    FAILED -> StatisticsCalculator_2
    FAILED -> Sorter_12
Sorter_12
    SORT_PARM = bknorm_vegref ALPHA ASCENDING
    SORTED -> AttributeRenamer
AttributeRenamer
    ATTR_TABLE:
      RENAME_SET_DEFAULT bknorm_fylke > fylke
      RENAME_SET_DEFAULT spesial_delvisOverlapp > delvisOverlapp
      RENAME_SET_DEFAULT spesial_delvisOverlapp_lengde > lengdeDelvisOverlapp
    -> BK Vinter normal vs spesial (writer XLSXW_1)
BK Vinter normal vs spesial (writer XLSXW_1)
    attributes: fylke number(6), bknorm_vegref string(32), bknorm_Bruksklassevinter string(30), spesial_Bruksklassevinter string(30), lengdeDelvisOverlapp number(20), delvisOverlapp string(30), bknorm_Strekningsbeskrivelse string(50), spesial_Strekningsbeskrivelse string(50), bknorm_nvdbid number(10), spesial_nvdbid number(10)
Note: BKvinter normal - spesial
StatisticsCalculator_2
    COMPUTE_HISTOGRAM = NO
    GROUP_BY = spesial_Bruksklassevinter bknorm_Bruksklassevinter
    PREPEND_ATTR_NAME_CHOICE = For multiple results only
    STATS_ATTRS = spesial_lengde
    SUM_ATTR = lengde_sum
    SUMMARY -> ExpressionEvaluator_2
ExpressionEvaluator_2
    ACTION = Overwrite Existing Attributes
    ATTRLIST = lengde_sum
    EXPRESSION = @round(@Value(lengde_sum)/1000,$(Avrunding))
    -> Sorter_2
Sorter_2
    SORT_PARM = lengde_sum NUMERIC DESCENDING
    SORTED -> BK_vinter_normal_-_spesial
BK_vinter_normal_-_spesial: Inspector [off]

Bookmark: Maks vogntoglengde
Tester_3
    BOOL_OP = OR
    TEST_CLAUSE = TEST @Value(bknorm_Maksvogntoglengde) = @Value(spesial_Maksvogntoglengde)
    FAILED -> StatisticsCalculator_3
    FAILED -> TestFilter_2
TestFilter_2
    DEFAULT_VALUE = <UNFILTERED>
    TEST_LIST = "BOOL_OP,AND,COMPOSITE_TEST,""""""<Unused>"""""",TEST_CLAUSE,TEST @Value(spesial_Maksvogntoglengde) >= @Value(bknorm_Maksvogntoglengde)",godemaks
    <UNFILTERED> -> Sorter_15
Sorter_15
    SORT_PARM = bknorm_vegref ALPHA ASCENDING
    SORTED -> AttributeRenamer_5
AttributeRenamer_5
    ATTR_TABLE:
      RENAME_SET_DEFAULT bknorm_fylke > fylke
      RENAME_SET_DEFAULT spesial_delvisOverlapp > delvisOverlapp
      RENAME_SET_DEFAULT spesial_delvisOverlapp_lengde > lengdeDelvisOverlapp
    -> Maksvogntoglengde_normal_spesia (writer XLSXW_1)
Maksvogntoglengde_normal_spesia (writer XLSXW_1)
    attributes: fylke number(6), bknorm_vegref string(32), bknorm_Bruksklasse string(30), spesial_Bruksklasse string(30), bknorm_Maksvogntoglengde number(20), spesial_Maksvogntoglengde number(20), lengdeDelvisOverlapp number(20), delvisOverlapp string(30), bknorm_Strekningsbeskrivelse string(50), spesial_Strekningsbeskrivelse string(50), bknorm_nvdbid number(10), spesial_nvdbid number(10)
Note: Maksvogntoglengde - spesial
StatisticsCalculator_3
    COMPUTE_HISTOGRAM = NO
    GROUP_BY = bknorm_Maksvogntoglengde spesial_Maksvogntoglengde
    PREPEND_ATTR_NAME_CHOICE = For multiple results only
    STATS_ATTRS = spesial_lengde
    SUM_ATTR = lengde_sum
    SUMMARY -> ExpressionEvaluator_3
ExpressionEvaluator_3
    ACTION = Overwrite Existing Attributes
    ATTRLIST = lengde_sum
    EXPRESSION = @round(@Value(lengde_sum)/1000,$(Avrunding))
    -> Sorter_3
Sorter_3
    SORT_PARM = lengde_sum NUMERIC DESCENDING
    SORTED -> Maksvogntoglengde_normal_-_spesial_2
Maksvogntoglengde_normal_-_spesial_2: Inspector

Bookmark: Bruksklasse normal - spesial
Tester_7
    BOOL_OP = OR
    TEST_CLAUSE = TEST @Value(bknorm_Bruksklasse) = @Value(spesial_Bruksklasse)
    FAILED -> StatisticsCalculator
    FAILED -> Sorter_11
Sorter_11
    SORT_PARM = bknorm_vegref ALPHA ASCENDING
    SORTED -> AttributeRenamer_2
AttributeRenamer_2
    ATTR_TABLE:
      RENAME_SET_DEFAULT bknorm_fylke > fylke
      RENAME_SET_DEFAULT spesial_delvisOverlapp > delvisOverlapp
      RENAME_SET_DEFAULT spesial_delvisOverlapp_lengde > lengdeDelvisOverlapp
    -> BK Normal vs spesial (writer XLSXW_1)
BK Normal vs spesial (writer XLSXW_1)
    attributes: fylke number(6), bknorm_vegref string(32), bknorm_Bruksklasse string(30), spesial_Bruksklasse string(30), lengdeDelvisOverlapp number(20), delvisOverlapp string(30), bknorm_Strekningsbeskrivelse string(50), spesial_Strekningsbeskrivelse string(50), bknorm_nvdbid number(10), spesial_nvdbid number(10)
Note: Bruksklasse normal - spesial
StatisticsCalculator
    COMPUTE_HISTOGRAM = NO
    GROUP_BY = spesial_Bruksklasse bknorm_Bruksklasse
    PREPEND_ATTR_NAME_CHOICE = For multiple results only
    STATS_ATTRS = spesial_lengde
    SUM_ATTR = lengde_sum
    SUMMARY -> ExpressionEvaluator
ExpressionEvaluator
    ACTION = Overwrite Existing Attributes
    ATTRLIST = lengde_sum
    EXPRESSION = @round(@Value(lengde_sum)/1000,$(Avrunding))
    -> Sorter
Sorter
    SORT_PARM = lengde_sum NUMERIC DESCENDING
    SORTED -> BK_normal_vs_spesial
BK_normal_vs_spesial: Inspector [off]

Bookmark: New Bookmark
Tester_11
    BOOL_OP = OR
    TEST_CLAUSE = TEST @Value(bknorm_Merknad) = @Value(spesial_Merknad)
    FAILED -> StatisticsCalculator_10
    FAILED -> Tester
Tester
    BOOL_OP = AND
    TEST_CLAUSE:
      TEST bknorm_Merknad ATTRIBUTE_IS_EMPTY ""
      TEST spesial_Merknad ATTRIBUTE_IS_EMPTY ""
    FAILED -> Sorter_17
Sorter_17
    SORT_PARM = bknorm_vegref ALPHA ASCENDING
    SORTED -> AttributeRenamer_7
AttributeRenamer_7
    ATTR_TABLE:
      RENAME_SET_DEFAULT bknorm_fylke > fylke
      RENAME_SET_DEFAULT spesial_delvisOverlapp > delvisOverlapp
      RENAME_SET_DEFAULT spesial_delvisOverlapp_lengde > lengdeDelvisOverlapp
    -> Merknad_normal_spesial (writer XLSXW_1)
Merknad_normal_spesial (writer XLSXW_1)
    attributes: fylke number(6), bknorm_vegref string(32), bknorm_Bruksklasse string(30), spesial_Bruksklasse string(30), bknorm_Merknad string(50), spesial_Merknad string(50), lengdeDelvisOverlapp number(20), delvisOverlapp string(30), bknorm_Strekningsbeskrivelse string(50), spesial_Strekningsbeskrivelse string(50), bknorm_nvdbid number(10), spesial_nvdbid number(10)
Note: Merknad normal - spesial
StatisticsCalculator_10
    COMPUTE_HISTOGRAM = NO
    GROUP_BY = bknorm_Merknad spesial_Merknad
    PREPEND_ATTR_NAME_CHOICE = For multiple results only
    STATS_ATTRS = spesial_lengde
    SUM_ATTR = lengde_sum
    SUMMARY -> ExpressionEvaluator_10
ExpressionEvaluator_10
    ACTION = Overwrite Existing Attributes
    ATTRLIST = lengde_sum
    EXPRESSION = @round(@Value(lengde_sum)/1000,$(Avrunding))
    -> Sorter_10
Sorter_10
    SORT_PARM = lengde_sum NUMERIC DESCENDING
    SORTED -> Merknad_normal_-_spesial_4
Merknad_normal_-_spesial_4: Inspector

Bookmark: Tømmer vs normaltransport
delvisOverlapp_2
    BKNORM_VEGREF = @Value(bknorm_vegref)
    VEGREF = @Value(vegref)
    PythonCaller_Output -> BulkAttributeRenamer_3
BulkAttributeRenamer_3
    ATTRCHOICE = All Attributes
    MODE_CHOICE = RENAME
    PATTERN_ACTION_DISP = ADDPREFIX
    REPLACE_STR = tommer_
    -> BulkAttributeRenamer_4
BulkAttributeRenamer_4
    ATTRCHOICE = All Attributes
    CASE_DISP = YES
    MODE_CHOICE = RENAME
    PATTERN_ACTION_DISP = STRINGREPLACE
    REPLACE_PATTERN = tommer_bknorm
    REPLACE_STR = bknorm
    -> Tester_4
    -> Tester_5
    -> Tester_6
    -> Tester_8
    -> Tester_9
Tester_5
    BOOL_OP = OR
    TEST_CLAUSE = TEST @Value(bknorm_Bruksklassevinter) = @Value(tommer_Bruksklassevinter)
    FAILED -> StatisticsCalculator_5
    FAILED -> Sorter_14
Sorter_14
    SORT_PARM = bknorm_vegref ALPHA ASCENDING
    SORTED -> AttributeRenamer_4
AttributeRenamer_4
    ATTR_TABLE:
      RENAME_SET_DEFAULT bknorm_fylke > fylke
      RENAME_SET_DEFAULT tommer_delvisOverlapp > delvisOverlapp
      RENAME_SET_DEFAULT tommer_delvisOverlapp_lengde > lengdeDelvisOverlapp
    -> BK Vinter normal vs tommer (writer XLSXW_1)
BK Vinter normal vs tommer (writer XLSXW_1)
    attributes: fylke number(6), bknorm_vegref string(32), bknorm_Bruksklassevinter string(30), tommer_Bruksklassevinter string(30), lengdeDelvisOverlapp number(20), delvisOverlapp string(30), bknorm_Strekningsbeskrivelse string(50), tommer_Strekningsbeskrivelse string(50), bknorm_nvdbid number(10), tommer_nvdbid number(10)
Note: BKvinter normal - tømmer
StatisticsCalculator_5
    COMPUTE_HISTOGRAM = NO
    GROUP_BY = tommer_Bruksklassevinter bknorm_Bruksklassevinter
    PREPEND_ATTR_NAME_CHOICE = For multiple results only
    STATS_ATTRS = tommer_lengde
    SUM_ATTR = lengde_sum
    SUMMARY -> ExpressionEvaluator_5
ExpressionEvaluator_5
    ACTION = Overwrite Existing Attributes
    ATTRLIST = lengde_sum
    EXPRESSION = @round(@Value(lengde_sum)/1000,$(Avrunding))
    -> Sorter_5
Sorter_5
    SORT_PARM = lengde_sum NUMERIC DESCENDING
    SORTED -> BK_vinter_normal_vs_tommer
BK_vinter_normal_vs_tommer: Inspector [off]

Bookmark: New Bookmark
Tester_4
    BOOL_OP = OR
    TEST_CLAUSE = TEST @Value(bknorm_Bruksklasse) = @Value(tommer_Bruksklasse)
    FAILED -> StatisticsCalculator_4
    FAILED -> Sorter_13
Sorter_13
    SORT_PARM = bknorm_vegref ALPHA ASCENDING
    SORTED -> AttributeRenamer_3
AttributeRenamer_3
    ATTR_TABLE:
      RENAME_SET_DEFAULT bknorm_fylke > fylke
      RENAME_SET_DEFAULT tommer_delvisOverlapp > delvisOverlapp
      RENAME_SET_DEFAULT tommer_delvisOverlapp_lengde > lengdeDelvisOverlapp
    -> BK Normal vs tommer (writer XLSXW_1)
BK Normal vs tommer (writer XLSXW_1)
    attributes: fylke number(6), bknorm_vegref string(32), bknorm_Bruksklasse string(30), tommer_Bruksklasse string(30), lengdeDelvisOverlapp number(20), delvisOverlapp string(30), bknorm_Strekningsbeskrivelse string(50), tommer_Strekningsbeskrivelse string(50), bknorm_nvdbid number(10), tommer_nvdbid number(10)
Note: Bruksklasse normal - tømmer
StatisticsCalculator_4
    COMPUTE_HISTOGRAM = NO
    GROUP_BY = tommer_Bruksklasse bknorm_Bruksklasse
    PREPEND_ATTR_NAME_CHOICE = For multiple results only
    STATS_ATTRS = tommer_lengde
    SUM_ATTR = lengde_sum
    SUMMARY -> ExpressionEvaluator_4
ExpressionEvaluator_4
    ACTION = Overwrite Existing Attributes
    ATTRLIST = lengde_sum
    EXPRESSION = @round(@Value(lengde_sum)/1000,$(Avrunding))
    -> Sorter_4
Sorter_4
    SORT_PARM = lengde_sum NUMERIC DESCENDING
    SORTED -> BK_normal_vs_tommer
BK_normal_vs_tommer: Inspector [off]

Bookmark: Maks vogntoglengde tømmer
Tester_6
    BOOL_OP = OR
    TEST_CLAUSE = TEST @Value(bknorm_Maksvogntoglengde) = @Value(tommer_Maksvogntoglengde)
    FAILED -> StatisticsCalculator_6
    FAILED -> TestFilter
TestFilter
    DEFAULT_VALUE = <UNFILTERED>
    TEST_LIST = "BOOL_OP,AND,COMPOSITE_TEST,""""""<Unused>"""""",TEST_CLAUSE,TEST @Value(tommer_Maksvogntoglengde) >= @Value(bknorm_Maksvogntoglengde)",godemaks
    <UNFILTERED> -> Sorter_16
Sorter_16
    SORT_PARM = bknorm_vegref ALPHA ASCENDING
    SORTED -> AttributeRenamer_6
AttributeRenamer_6
    ATTR_TABLE:
      RENAME_SET_DEFAULT bknorm_fylke > fylke
      RENAME_SET_DEFAULT tommer_delvisOverlapp > delvisOverlapp
      RENAME_SET_DEFAULT tommer_delvisOverlapp_lengde > lengdeDelvisOverlapp
    -> Maksvogntoglengde Normal tomme (writer XLSXW_1)
Maksvogntoglengde Normal tomme (writer XLSXW_1)
    attributes: fylke number(6), bknorm_vegref string(32), bknorm_Bruksklasse string(30), tommer_Bruksklasse string(30), bknorm_Maksvogntoglengde number(30), tommer_Maksvogntoglengde number(30), lengdeDelvisOverlapp number(20), delvisOverlapp string(30), bknorm_Strekningsbeskrivelse string(50), tommer_Strekningsbeskrivelse string(50), bknorm_nvdbid number(10), tommer_nvdbid number(10)
Note: Maks vogntoglengde normal - tømmer
StatisticsCalculator_6
    COMPUTE_HISTOGRAM = NO
    GROUP_BY = bknorm_Maksvogntoglengde tommer_Maksvogntoglengde
    PREPEND_ATTR_NAME_CHOICE = For multiple results only
    STATS_ATTRS = tommer_lengde
    SUM_ATTR = lengde_sum
    SUMMARY -> ExpressionEvaluator_6
ExpressionEvaluator_6
    ACTION = Overwrite Existing Attributes
    ATTRLIST = lengde_sum
    EXPRESSION = @round(@Value(lengde_sum)/1000,$(Avrunding))
    -> Sorter_6
Sorter_6
    SORT_PARM = lengde_sum NUMERIC DESCENDING
    SORTED -> Maksvogntoglengde_normal_tommer
Maksvogntoglengde_normal_tommer: Inspector

Bookmark: New Bookmark
Tester_8
    BOOL_OP = OR
    TEST_CLAUSE = TEST @Value(bknorm_Strekningsbeskrivelse) = @Value(tommer_Strekningsbeskrivelse)
    FAILED -> StatisticsCalculator_7
Note: Strekningsbeskrivelse normal - tømmer
StatisticsCalculator_7
    COMPUTE_HISTOGRAM = NO
    GROUP_BY = bknorm_Strekningsbeskrivelse tommer_Strekningsbeskrivelse
    PREPEND_ATTR_NAME_CHOICE = For multiple results only
    STATS_ATTRS = tommer_lengde
    SUM_ATTR = lengde_sum
    SUMMARY -> ExpressionEvaluator_7
ExpressionEvaluator_7
    ACTION = Overwrite Existing Attributes
    ATTRLIST = lengde_sum
    EXPRESSION = @round(@Value(lengde_sum)/1000,$(Avrunding))
    -> Sorter_7
Sorter_7
    SORT_PARM = lengde_sum NUMERIC DESCENDING
    SORTED -> Strekningsbeskrivelse_normal_tommer_2
Strekningsbeskrivelse_normal_tommer_2: Inspector [off]

Bookmark: Merknad normal - tømmer
Tester_9
    BOOL_OP = OR
    TEST_CLAUSE = TEST @Value(bknorm_Merknad) = @Value(tommer_Merknad)
    FAILED -> StatisticsCalculator_8
    FAILED -> Tester_12
Tester_12
    BOOL_OP = AND
    TEST_CLAUSE:
      TEST bknorm_Merknad ATTRIBUTE_IS_EMPTY ""
      TEST spesial_Merknad ATTRIBUTE_IS_EMPTY ""
    FAILED -> Sorter_18
Sorter_18
    SORT_PARM = bknorm_vegref ALPHA ASCENDING
    SORTED -> AttributeRenamer_8
AttributeRenamer_8
    ATTR_TABLE:
      RENAME_SET_DEFAULT bknorm_fylke > fylke
      RENAME_SET_DEFAULT tommer_delvisOverlapp > delvisOverlapp
      RENAME_SET_DEFAULT tommer_delvisOverlapp_lengde > lengdeDelvisOverlapp
    -> Merknad Normal tommer (writer XLSXW_1)
Merknad Normal tommer (writer XLSXW_1)
    attributes: fylke number(6), bknorm_vegref string(32), bknorm_Bruksklasse string(30), tommer_Bruksklasse string(30), bknorm_Merknad string(50), tommer_Merknad string(50), lengdeDelvisOverlapp number(20), delvisOverlapp string(30), bknorm_Strekningsbeskrivelse string(50), tommer_Strekningsbeskrivelse string(50), bknorm_nvdbid number(10), tommer_nvdbid number(10)
Note: Merknad normal - tømmer
StatisticsCalculator_8
    COMPUTE_HISTOGRAM = NO
    GROUP_BY = tommer_Merknad bknorm_Merknad
    PREPEND_ATTR_NAME_CHOICE = For multiple results only
    STATS_ATTRS = tommer_lengde
    SUM_ATTR = lengde_sum
    SUMMARY -> ExpressionEvaluator_8
ExpressionEvaluator_8
    ACTION = Overwrite Existing Attributes
    ATTRLIST = lengde_sum
    EXPRESSION = @round(@Value(lengde_sum)/1000,$(Avrunding))
    -> Sorter_8
Sorter_8
    SORT_PARM = lengde_sum NUMERIC DESCENDING
    SORTED -> Merknad_normal_tommer_3
Merknad_normal_tommer_3: Inspector

FME custom transformer delvisOverlapp

Parameters:
- BKNORM_VEGREF = @Value(bknorm_vegref)   # bknorm_vegref
- VEGREF = @Value(vegref)   # vegref

Tester_Input (input)
    -> Tester

Bookmark: New Bookmark
Tester
    BOOL_OP = OR
    TEST_CLAUSE = TEST @Value(bknorm_vegref) = @Value(vegref)
    PASSED -> PythonCaller_Output (output)
    FAILED -> StringSearcher
StringSearcher
    CASE = no
    MATCHES_ATTR = bknorm_vegrefliste
    REGEXP = \d+
    STRING_TO_SEARCH = @Value(bknorm_vegref)
    MATCHED -> StringSearcher_2
StringSearcher_2
    CASE = no
    MATCHES_ATTR = vegrefliste
    REGEXP = \d+
    STRING_TO_SEARCH = @Value(vegref)
    MATCHED -> StringSearcher_3
StringSearcher_3
    CASE = no
    MATCHES_ATTR = bknorm_vegrefliste
    REGEXP = \d+
    STRING_TO_SEARCH = @Value(bknorm_vegref)
    MATCHED -> AttributeSplitter
AttributeSplitter
    ATTR_NAME = vegref
    DELIMITER = " "
    DROP_EMPTY_PARTS = No
    LIST_NAME = _list
    TRIM_OPTION = Both
    -> PythonCaller
PythonCaller
    NEW_ATTRIBUTES = delvisOverlapp delvisOverlapp_lengde
    PYTHONSOURCE:
      import fme
      import fmeobjects
      # Template Function interface:
      # When using this function, make sure its name is set as the value of
      # the 'Class or Function to Process Features' transformer parameter
      def lagmeteroverlapp(feature):




          vreftekstliste = feature.getAttribute( '_list{}')
          vrefliste1 = feature.getAttribute( 'vegrefliste{}.match')
          vrefliste2 = feature.getAttribute( 'bknorm_vegrefliste{}.match')
          bknorm_lengde = feature.getAttribute( 'bknorm_lengde')
          lengde = feature.getAttribute( 'lengde')
          bknorm_vegref = feature.getAttribute( 'bknorm_vegref')
          vegref = feature.getAttribute( 'vegref')

          if len(vrefliste1) == 5 and len(vrefliste2) == 5 and len(vreftekstliste) == 4:

              delvisoverlapp_lengde = min( int(vrefliste1[4]), int(vrefliste2[4]) )  - max( int(vrefliste1[3]), int(vrefliste2[3]) )

              delvisoverlapp = ' '.join( vreftekstliste[0:2] ) + 'm' + \
                  str( max( int(vrefliste1[3]), int(vrefliste2[3]) ) ) + '-' + \
                  str( min( int(vrefliste1[4]), int(vrefliste2[4]) ) )

              feature.setAttribute( 'delvisOverlapp', delvisoverlapp)
              feature.setAttribute( 'delvisOverlapp_lengde', delvisoverlapp_lengde)

          elif float(lengde) < 0:

              feature.setAttribute( 'delvisOverlapp', vegref)
              feature.setAttribute( 'delvisOverlapp_lengde', 0)

          elif float(bknorm_lengde) < 0:

              feature.setAttribute( 'delvisOverlapp', bknorm_vegref)
              feature.setAttribute( 'delvisOverlapp_lengde', 0)




      #    @Value(_list{0}) @Value(_list{1}) @Value(_list{2}) m(@max(@Value(vegrefliste{3}.match),@
      #
      #    Value(bknorm_vegrefliste{3}.match))-@min(@Value(bknorm_vegrefliste{4}.match),@Value(vegrefliste{4}.match))
    PYTHONSYMBOL = lagmeteroverlapp
    -> PythonCaller_Output (output)
PythonCaller_Output (output)
