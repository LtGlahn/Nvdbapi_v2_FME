FME workspace nvdbapi_V2_vegbredde_alletyper.fmw

Parameters:
- apiFetchObjectURL = https://www.vegvesen.no/nvdb/api/v2/vegobjekter/   # URL to NVDB api /vegobjekter end point (v2)
- objektTypeID = 904   # ID of object type from NVDB api
- antall = 1000   # Antall objekter per iterasjon (maks 1000)
- DestDataset_GEOPACKAGE = C:\DATA\leveranser\viatech_vegdekke_metodefil\vegbredde.gpkg   # GeoPackage File

Writers:
- GEOPACKAGE_1: GEOPACKAGE to $(DestDataset_GEOPACKAGE)

Creator
    GEOMTYPE = Geometry Object
    NUM = 1
    CREATED -> AttributeCreator
    CREATED -> AttributeCreator_6
    CREATED -> AttributeCreator_5
vegbredde538 (writer GEOPACKAGE_1)
    attributes: vegobjektid text(200), Vegbredde_ totalt text(200), Dekkebredde text(200), Målemetode text(200), Kjørebanebredde text(200), Dataopprinnelse text(200), Dato registrert text(200), versjon text(200), vegref text(200), frameter text(200), tilmeter text(200), fylke text(200), hp text(200), vegkategori text(200), kommune text(200), vegnummer text(200), vegstatus text(200), veglenkeid text(200), fra_posisjon text(200), til_posisjon text(200), stedfesting text(200)
vegbreddestat647 (writer GEOPACKAGE_1)
    attributes: vegobjektid text(200), Opprettet dato text(200), Stedsangivelse_ fra_til text(200), Geografisk oppløsning text(200), Minimumsdato_ grunnlag text(200), Maksimumsdato_ grunnlag text(200), Midlere dekkebredde text(200), Midlere kjørebanebredde text(200), Midlere vegbredde text(200), Dekkeareal text(200), Målt _ text(200), Lengde text(200), Dekkebreddefordeling text(200), Kjørebanebreddefordeling text(200), Vegbreddefordeling text(200), versjon text(200), vegref text(200), frameter text(200), tilmeter text(200), fylke text(200), hp text(200), vegkategori text(200), kommune text(200), vegnummer text(200), vegstatus text(200), veglenkeid text(200), fra_posisjon text(200), til_posisjon text(200), stedfesting text(200)

Bookmark: 838
AttributeCreator
    ATTR_LIST = vegobjektURI,$(apiFetchObjectURL)838?inkluder=alle&srid=32633&antall=$(antall)
    -> AttributeCreator_3
Note: Områdefilter / fylke=14 (Sogn og Fjordane)
AttributeCreator_3
    ATTR_LIST = omradefilter,kommune=1432
    -> AttributeCreator_4
    -> loop_fetchdata [HTTPFetcher_Input]
loop_fetchdata
    VEGOBJEKTURI = @Value(vegobjektURI)
    Tester_Passed -> AttributeCreator_2
    Tester_Failed -> DONE
DONE: Inspector [off]
Note: AttributeCreator_2 [AttributeCreator] / Attributes To Set: Attribute NameValueDekkebredde<not set>Dekkebredde, min<not set>Dekkebredde, maks<not set>Dekkebredde, median<not set>Dekkebredde, normal<not set>Vegbredde<not set>Vegbredde, min<not set>Vegbredde, maks<not set>Kjørebanebredde<not set>Kjørebanebredde, min<not set>Kjørebanebredde, maks<not set>Grunnlag<not set>Målemetode grunnlag<not set>Dato grunnlag<not set>Kvalitet grunnlag<not set>Beregningsinfo<not set>
AttributeCreator_2
    ATTR_LIST = Dekkebredde,,Dekkebredde, min,,Dekkebredde, maks,,Dekkebredde, median,,Dekkebredde, normal,,Vegbredde,,Vegbredde, min,,Vegbredde, maks,,Kjørebanebredde,,Kjørebanebredde, min,,Kjørebanebredde, maks,,Grunnlag,,Målemetode grunnlag,,Dato grunnlag,,Kvalitet grunnlag,,Beregningsinfo,
    -> XMLFeatureMapper_3
Note: This is where the magic happens! / xml=>FME features
XMLFeatureMapper_3
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = id versjon sist_modifisert objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_5
Note: Kun objekter med gyldig stedfesting / (F.eks. ingen historiske bruer)
Tester_5
    BOOL_OP = OR
    TEST_CLAUSE = TEST wkt NOT_ATTRIBUTE_IS_MISSING ""
    PASSED -> AttributeRemover
    FAILED -> Ugyldig_stedfesting
AttributeRenamer
    ATTR_TABLE = RENAME_SET_DEFAULT id > vegobjektid
    -> vegbredde838 (writer GEOPACKAGE_1)
vegbredde838 (writer GEOPACKAGE_1)
    attributes: vegobjektid text(200), Dekkebredde text(200), Dekkebredde_ min text(200), Dekkebredde_ maks text(200), Dekkebredde_ median text(200), Dekkebredde_ normal text(200), Vegbredde text(200), Vegbredde_ min text(200), Vegbredde_ maks text(200), Kjørebanebredde text(200), Kjørebanebredde_ min text(200), Kjørebanebredde_ maks text(200), Grunnlag text(200), Målemetode grunnlag text(200), Dato grunnlag text(200), Kvalitet grunnlag text(200), Beregningsinfo text(200), versjon text(200), vegref text(200), frameter text(200), tilmeter text(200), fylke text(200), hp text(200), vegkategori text(200), kommune text(200), vegnummer text(200), vegstatus text(200), veglenkeid text(200), fra_posisjon text(200), til_posisjon text(200),
      stedfesting text(200)
Note: Set coordinate system / EPSG:25833 / (Not 32633, error in NVDB api documentation)
838_vegbredde__beregnet: Inspector
Ugyldig_stedfesting: Inspector [off]
Note: Føyer til filter
AttributeCreator_4
    ATTR_LIST = vegobjektURI,@Value(vegobjektURI)&@Value(omradefilter)

Bookmark: Split object into individual road segments
AttributeRemover
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_3
AttributeRemover_3
    LIST_ATTRS = kontraktsomrade{} region{} riksvegrute{}
    REMOVE_ATTRS = href,objektTypeId,objektTypeNavn,sist_modifisert,srid,Veglenkeposisjon,wkt
    -> ListExploder
ListExploder
    ATTR_ACCUM_MODE = Merge Incoming List
    ATTR_CONFLICT_RES = Use Incoming List
    INDEX_ATTR = _element_index
    LIST_ATTR = segment{}
    LIST_FOUND -> AttributeExposer
    NOT_FOUND -> ListExploder_NotFound
AttributeExposer
    ATTR_LIST = vegref,meter,frameter,tilmeter,fylke,hp,vegkategori,kommune,vegnummer,vegstatus,veglenkeid,wkt,fra_posisjon,til_posisjon,stedfesting
    -> CoordinateSystemSetter
CoordinateSystemSetter
    COORDSYS = EPSG:25833
    -> GeometryReplacer_2
GeometryReplacer_2
    KIND_LONG = OGC Well Known Text
    REMOVE_ATTRIBUTE = Yes
    SOURCE = @Value(wkt)
    -> AttributeRemover_2
AttributeRemover_2
    REMOVE_ATTRS = meter,wkt,_element_index,egengeometri,segment
    -> 838_vegbredde__beregnet
    -> AttributeRenamer
ListExploder_NotFound: Inspector

Bookmark: 583
AttributeCreator_6
    ATTR_LIST = vegobjektURI,$(apiFetchObjectURL)583?inkluder=alle&srid=32633&antall=$(antall)
    -> AttributeCreator_8
Note: Områdefilter / fylke=14 (Sogn og Fjordane)
AttributeCreator_8
    ATTR_LIST = omradefilter,kommune=1432
    -> AttributeCreator_9
    -> loop_fetchdata_2 [HTTPFetcher_Input]
loop_fetchdata_2
    VEGOBJEKTURI = @Value(vegobjektURI)
    Tester_Passed -> AttributeCreator_7
    Tester_Failed -> DONE_2
DONE_2: Inspector [off]
Note: AttributeCreator_7 [AttributeCreator] / Attributes To Set: Attribute NameValueVegbredde, totalt<not set>Dekkebredde<not set>Målemetode<not set>Kjørebanebredde<not set>Dataopprinnelse<not set>Dato registrert<not set>
AttributeCreator_7
    ATTR_LIST = Vegbredde, totalt,,Dekkebredde,,Målemetode,,Kjørebanebredde,,Dataopprinnelse,,Dato registrert,
    -> XMLFeatureMapper_2
Note: This is where the magic happens! / xml=>FME features
XMLFeatureMapper_2
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = id versjon sist_modifisert objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_2
Note: Kun objekter med gyldig stedfesting / (F.eks. ingen historiske bruer)
Tester_2
    BOOL_OP = OR
    TEST_CLAUSE = TEST wkt NOT_ATTRIBUTE_IS_MISSING ""
    PASSED -> AttributeRemover_4
    FAILED -> Ugyldig_stedfesting_2
Ugyldig_stedfesting_2: Inspector [off]
AttributeRenamer_2
    ATTR_TABLE = RENAME_SET_DEFAULT id > vegobjektid
    -> vegbredde538 (writer GEOPACKAGE_1)
Note: Set coordinate system / EPSG:25833 / (Not 32633, error in NVDB api documentation)
538_Vegbredde: Inspector
Note: Føyer til filter
AttributeCreator_9
    ATTR_LIST = vegobjektURI,@Value(vegobjektURI)&@Value(omradefilter)

Bookmark: Split object into individual road segments
AttributeRemover_4
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_5
AttributeRemover_5
    LIST_ATTRS = kontraktsomrade{} region{} riksvegrute{}
    REMOVE_ATTRS = href,objektTypeId,objektTypeNavn,sist_modifisert,srid,Veglenkeposisjon,wkt
    -> ListExploder_2
ListExploder_2
    ATTR_ACCUM_MODE = Merge Incoming List
    ATTR_CONFLICT_RES = Use Incoming List
    INDEX_ATTR = _element_index
    LIST_ATTR = segment{}
    LIST_FOUND -> AttributeExposer_2
    NOT_FOUND -> ListExploder_NotFound_2
AttributeExposer_2
    ATTR_LIST = vegref,meter,frameter,tilmeter,fylke,hp,vegkategori,kommune,vegnummer,vegstatus,veglenkeid,wkt,fra_posisjon,til_posisjon,stedfesting
    -> CoordinateSystemSetter_2
CoordinateSystemSetter_2
    COORDSYS = EPSG:25833
    -> GeometryReplacer_3
GeometryReplacer_3
    KIND_LONG = OGC Well Known Text
    REMOVE_ATTRIBUTE = Yes
    SOURCE = @Value(wkt)
    -> AttributeRemover_6
AttributeRemover_6
    REMOVE_ATTRS = meter,wkt,_element_index,egengeometri,segment
    -> 538_Vegbredde
    -> AttributeRenamer_2
ListExploder_NotFound_2: Inspector

Bookmark: 647
AttributeCreator_5
    ATTR_LIST = vegobjektURI,$(apiFetchObjectURL)647?inkluder=alle&srid=32633&antall=$(antall)
    -> AttributeCreator_11
Note: Områdefilter / fylke=14 (Sogn og Fjordane)
AttributeCreator_11
    ATTR_LIST = omradefilter,kommune=1432
    -> AttributeCreator_12
    -> loop_fetchdata_3 [HTTPFetcher_Input]
loop_fetchdata_3
    VEGOBJEKTURI = @Value(vegobjektURI)
    Tester_Passed -> AttributeCreator_10
    Tester_Failed -> DONE_3
DONE_3: Inspector [off]
Note: AttributeCreator_10 [AttributeCreator] / Attributes To Set: Attribute NameValueOpprettet dato<not set>Stedsangivelse, fra-til<not set>Geografisk oppløsning<not set>Minimumsdato, grunnlag<not set>Maksimumsdato, grunnlag<not set>Midlere dekkebredde<not set>Midlere kjørebanebredde<not set>Midlere vegbredde<not set>Dekkeareal<not set>Målt %<not set>Lengde<not set>Dekkebreddefordeling<not set>Kjørebanebreddefordeling<not set>Vegbreddefordeling<not set>
AttributeCreator_10
    ATTR_LIST = Opprettet dato,,Stedsangivelse, fra-til,,Geografisk oppløsning,,Minimumsdato, grunnlag,,Maksimumsdato, grunnlag,,Midlere dekkebredde,,Midlere kjørebanebredde,,Midlere vegbredde,,Dekkeareal,,Målt %,,Lengde,,Dekkebreddefordeling,,Kjørebanebreddefordeling,,Vegbreddefordeling,
    -> XMLFeatureMapper_4
Note: This is where the magic happens! / xml=>FME features
XMLFeatureMapper_4
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = id versjon sist_modifisert objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_3
Note: Kun objekter med gyldig stedfesting / (F.eks. ingen historiske bruer)
Tester_3
    BOOL_OP = OR
    TEST_CLAUSE = TEST wkt NOT_ATTRIBUTE_IS_MISSING ""
    PASSED -> AttributeRemover_7
    FAILED -> Ugyldig_stedfesting_3
Ugyldig_stedfesting_3: Inspector [off]
AttributeRenamer_3
    ATTR_TABLE = RENAME_SET_DEFAULT id > vegobjektid
    -> 647_stat_vegbredde
    -> vegbreddestat647 (writer GEOPACKAGE_1)
Note: Set coordinate system / EPSG:25833 / (Not 32633, error in NVDB api documentation)
647_stat_vegbredde: Inspector
Note: Føyer til filter
AttributeCreator_12
    ATTR_LIST = vegobjektURI,@Value(vegobjektURI)&@Value(omradefilter)

Bookmark: Split object into individual road segments
AttributeRemover_7
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_8
AttributeRemover_8
    LIST_ATTRS = kontraktsomrade{} region{} riksvegrute{}
    REMOVE_ATTRS = href,objektTypeId,objektTypeNavn,sist_modifisert,srid,Veglenkeposisjon,wkt
    -> ListExploder_3
ListExploder_3
    ATTR_ACCUM_MODE = Merge Incoming List
    ATTR_CONFLICT_RES = Use Incoming List
    INDEX_ATTR = _element_index
    LIST_ATTR = segment{}
    LIST_FOUND -> AttributeExposer_3
    NOT_FOUND -> ListExploder_NotFound_3
AttributeExposer_3
    ATTR_LIST = vegref,meter,frameter,tilmeter,fylke,hp,vegkategori,kommune,vegnummer,vegstatus,veglenkeid,wkt,fra_posisjon,til_posisjon,stedfesting
    -> CoordinateSystemSetter_3
CoordinateSystemSetter_3
    COORDSYS = EPSG:25833
    -> GeometryReplacer_4
GeometryReplacer_4
    KIND_LONG = OGC Well Known Text
    REMOVE_ATTRIBUTE = Yes
    SOURCE = @Value(wkt)
    -> AttributeRemover_9
AttributeRemover_9
    REMOVE_ATTRS = meter,wkt,_element_index,egengeometri,segment
    -> AttributeRenamer_3
ListExploder_NotFound_3: Inspector

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    AUTH_METHOD = Basic
    ERROR_ATTR = _error
    FOLLOW_REDIRECTS = Yes
    PROXY_AUTH_METHOD = Basic
    REQUEST_HEADER:
      Accept:application/vnd.vegvesen.nvdb-v2+xml
      X-Client:FME http caller
      X-Kontaktperson: Jan Kristian Jensen
    RESPONSE_HEADER_LIST_ATTR = _headers
    SAVE_FILE = No
    STATUS_CODE_ATTR = _http_status_code
    TARGET_ATTR = _url_contents
    TARGET_URL = @Value(vegobjektURI)
    USE_COOKIES = No
    VERIFY_SSL_CERTIFICATES = Yes
    -> XMLFeatureMapper_3
    <REJECTED> -> HTTPFetcher__Rejected_
XMLFeatureMapper_3
    ATTRIBUTE_XML = _url_contents
    CONFIGURATION_TYPE = Embedded xfMap script
    FEATURE_COUNT_PER_XML = _xml_feature_count_
    FEATURE_TYPE_ATTR = _xml_feature_type_
    MERGE_ATTRS = Yes
    NEW_ATTRIBUTES = antall returnert start href
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    XML_INPUT_TYPE = Attribute with XML document
    XML_SOURCE_NAME = _xml_source_
    MAPPED -> Tester
Tester
    BOOL_OP = OR
    TEST_CLAUSE = TEST @Value(returnert) > 0
    PASSED -> Tester_Passed (output)
    PASSED -> AttributeCreator_4
    FAILED -> Tester_Failed (output)
