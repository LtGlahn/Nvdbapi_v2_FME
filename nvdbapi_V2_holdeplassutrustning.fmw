FME workspace nvdbapi_V2_holdeplassutrustning.fmw

Parameters:
- apiFetchObjectURL = https://www.vegvesen.no/nvdb/api/v2/vegobjekter/   # URL to NVDB api /vegobjekter end point (v2)
- objektTypeID = 487   # ID of object type from NVDB api
- antall = 1000   # Antall objekter per iterasjon (maks 1000)

Creator
    GEOMTYPE = Geometry Object
    NUM = 1
    CREATED -> AttributeCreator
AttributeCreator
    ATTR_LIST = vegobjektURI,$(apiFetchObjectURL)$(objektTypeID)?inkluder=alle&srid=32633&antall=$(antall)
    -> AttributeCreator_4
    -> AttributeCreator_3 [off]
    -> loop_fetchdata
Note: Egenskapsfilter (property filter) / Toll (takst) >= 20 kr
AttributeCreator_3
    ATTR_LIST = vegobjektURI,@Value(vegobjektURI)&egenskap="1820>=20"
    -> AttributeCreator_4
Note: Are filter (property filter) / Region=3
AttributeCreator_4 [off]
    ATTR_LIST = vegobjektURI,@Value(vegobjektURI)&kommune=1103
    -> loop_fetchdata
loop_fetchdata
    VEGOBJEKTURI = @Value(vegobjektURI)
    Tester_Failed -> DONE
    Tester_Passed -> AttributeCreator_2
Note: Explisit define the attributes! / Must be tuned to your object type definition! / (Just ignore the properties you don't need) / Takst liten bil = / Takst stor bil = / Bomstasjonstype = / Navn bomstasjon = / ... and so on
AttributeCreator_2
    ATTR_LIST = Trafikkretning, geografisk,"",NHR_Holdeplassnummer,"",Holdeplassnummer, alternativ,"",NHR_Holdeplassnavn,"",Holdeplassnavn, alternativ,"",NHR_Stoppunktnummer,"",Stoppunktnummer_alternativ,"",Etableringsår,"",Tilleggsinformasjon,"",Eier,"",Vedlikeholdsansvarlig,"",Prosjektreferanse,""
    -> XMLFeatureMapper_3
Note: This is where the magic happens! / xml=>FME features
XMLFeatureMapper_3
    NEW_ATTRIBUTES = sist_modifisert id objektTypeId objektTypeNavn region{} kontraktsomrade{} riksvegrute{} wkt srid egengeometri strekningslengde segment{}
    XML_INPUT_TYPE = Attribute with XML document
    ATTRIBUTE_XML = _url_contents
    CONFIGURATION_TYPE = Single xfMap file
    FEATURE_TYPE_ATTR = _xml_feature_type_
    FEATURE_COUNT_PER_XML = _xml_feature_count_
    MERGE_ATTRS = No
    SINGLE_XFMAP = $(FME_MF_DIR)xfmapDefintion_nvdbapi2fme_V2.xml
    XML_SOURCE_NAME = _xml_source_
    MAPPED -> Tester
Tester
    BOOL_OP = OR
    TEST_CLAUSE = TEST wkt NOT_ATTRIBUTE_IS_MISSING ""
    TEST_MODE = Automatic
    TEST_DESCRIPTION = ""
    PASSED -> CoordinateSystemSetter
    FAILED -> Tester_Failed
Note: Set coordinate system / EPSG:25833 / (Not 32633, error in NVDB api documentation)
CoordinateSystemSetter
    COORDSYS = EPSG:25833
    -> GeometryReplacer
Note: Spatial is special! / Read coordinates from attribute / OGC well known text
GeometryReplacer
    SOURCE = @Value(wkt)
    KIND_LONG = OGC Well Known Text
    REMOVE_ATTRIBUTE = No
    -> AttributeRemover
AttributeRemover
    REMOVE_ATTRS = _creation_instance,_error,_http_status_code,_url_contents,_xml_feature_count_,_xml_feature_type_,_xml_source_,strekningslengde,vegobjektURI,antall,returnert,start
    LIST_ATTRS = _headers{} _headers{}.name _headers{}.value
    -> PythonCaller
    -> AttributeRemover_Output
Note: Using pythonCaller to get data from list
PythonCaller
    PYTHONSOURCE:
      import fmeobjects
      import re
      import json


      def liste2egenskaper( feature ):

          vegref =  feature.getAttribute('segment{0}.vegref' )
          fylke =  feature.getAttribute('segment{0}.fylke' )


          kat = feature.getAttribute('segment{0}.vegkategori' )
          status = feature.getAttribute('segment{0}.vegstatus' )
          vegnr = feature.getAttribute('segment{0}.vegnummer' )
          hp = feature.getAttribute('segment{0}.hp' )
          frameter = feature.getAttribute('segment{0}.frameter' )
          tilmeter = feature.getAttribute('segment{0}.tilmeter' )

          mittvegnr = kat + status.lower() + vegnr

          feature.setAttribute("Vegreferanse", vegref)
          feature.setAttribute("Fylke", fylke)
          feature.setAttribute("hp", hp)
          feature.setAttribute("frameter", frameter)
          feature.setAttribute("tilmeter", tilmeter)
       #   feature.setAttribute("Vegnr", mittvegnr)
    PYTHONSYMBOL = liste2egenskaper
    NEW_ATTRIBUTES = Vegreferanse Fylke hp frameter tilmeter
    -> AttributeRemover_3
    -> Holdeplassutrustning
AttributeRemover_3
    REMOVE_ATTRS = _error,_http_status_code,_url_contents,_xml_feature_count_,_xml_feature_type_,_xml_source_,Geometri, punkt,href,objektTypeId,objektTypeNavn,sist_modifisert,srid,Veglenkeposisjon,vegobjektURI,wkt
    LIST_ATTRS = _headers{} _headers{}.name _headers{}.value kontraktsomrade{} region{} riksvegrute{} segment{}
Note: Technically, we're done now!
Holdeplassutrustning: Inspector
AttributeRemover_Output: Inspector [off]
Tester_Failed: Inspector
Note: explisit define your attributes
DONE: Inspector [off]

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    RESPONSE_HEADER_LIST_ATTR = _headers
    SAVE_FILE = No
    TARGET_URL = @Value(vegobjektURI)
    PROXY_AUTH_METHOD = Basic
    USE_COOKIES = No
    VERIFY_SSL_CERTIFICATES = Yes
    AUTH_METHOD = Basic
    ERROR_ATTR = _error
    REQUEST_HEADER:
      Accept:application/vnd.vegvesen.nvdb-v2+xml
      X-Client:FME http caller
      X-Kontaktperson: Jan Kristian Jensen
    TARGET_ATTR = _url_contents
    STATUS_CODE_ATTR = _http_status_code
    FOLLOW_REDIRECTS = Yes
    -> XMLFeatureMapper_3
    <REJECTED> -> HTTPFetcher__Rejected_
XMLFeatureMapper_3
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    NEW_ATTRIBUTES = antall returnert start href
    XML_INPUT_TYPE = Attribute with XML document
    ATTRIBUTE_XML = _url_contents
    CONFIGURATION_TYPE = Embedded xfMap script
    FEATURE_TYPE_ATTR = _xml_feature_type_
    FEATURE_COUNT_PER_XML = _xml_feature_count_
    MERGE_ATTRS = Yes
    XML_SOURCE_NAME = _xml_source_
    MAPPED -> Tester
Tester
    BOOL_OP = OR
    TEST_CLAUSE = TEST @Value(returnert) > 0
    TEST_MODE = Automatic
    TEST_DESCRIPTION = ""
    PASSED -> Tester_Passed (output)
    FAILED -> Tester_Failed (output)
    PASSED -> AttributeCreator_4
