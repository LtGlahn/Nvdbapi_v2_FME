FME workspace nvdbapi_V2_bru_vegbru.fmw

Parameters:
- apiFetchObjectURL = https://www.vegvesen.no/nvdb/api/v2/vegobjekter/   # URL to NVDB api /vegobjekter end point (v2)
- objektTypeID = 60   # ID of object type from NVDB api
- antall = 1000   # Antall objekter per iterasjon (maks 1000)

Creator
    NUM = 1
    GEOMTYPE = Geometry Object
    CREATED -> AttributeCreator
AttributeCreator
    ATTR_LIST = vegobjektURI,$(apiFetchObjectURL)$(objektTypeID)?inkluder=alle&srid=32633&antall=$(antall)
    -> AttributeCreator_3
Note: Egenskapsfilter / Alle bruer av typer "Vegbru" med lengde over 20 m (evt uten verdi for lengde) / egenskap="1263=7304 AND (1313 >= 20 OR 1313=null)"
AttributeCreator_3
    ATTR_LIST = egenskapsfilter,egenskap="1263=7304 AND (1313 >= 20 OR 1313=null)"
    -> loop_fetchdata
loop_fetchdata
    VEGOBJEKTURI = @Value(vegobjektURI)
    Tester_Failed -> DONE
    Tester_Passed -> AttributeCreator_2
DONE: Inspector [off]
Note: Explisit define the attributes! / Must be tuned to your object type definition! / (Just ignore the properties you don't need)
AttributeCreator_2
    ATTR_LIST = Brukategori,"",Byggverkstype,"",Lengde,"",Nummer,"",Navn,""
    -> XMLFeatureMapper_3
Note: This is where the magic happens! / xml=>FME features
XMLFeatureMapper_3
    SINGLE_XFMAP = $(FME_MF_DIR)xfmapDefintion_nvdbapi2fme_V2.xml
    XML_SOURCE_NAME = _xml_source_
    ATTRIBUTE_XML = _url_contents
    MERGE_ATTRS = No
    CONFIGURATION_TYPE = Single xfMap file
    FEATURE_COUNT_PER_XML = _xml_feature_count_
    NEW_ATTRIBUTES = sist_modifisert id objektTypeId objektTypeNavn region{} kontraktsomrade{} riksvegrute{} wkt srid egengeometri strekningslengde segment{}
    XML_INPUT_TYPE = Attribute with XML document
    FEATURE_TYPE_ATTR = _xml_feature_type_
    MAPPED -> CoordinateSystemSetter
Note: Set coordinate system / EPSG:25833 / (Not 32633, error in NVDB api documentation)
CoordinateSystemSetter
    COORDSYS = EPSG:25833
    -> Tester_5
Note: Kun objekter med gyldig stedfesting / (F.eks. ingen historiske bruer)
Tester_5
    TEST_CLAUSE = TEST wkt NOT_ATTRIBUTE_IS_MISSING ""
    TEST_DESCRIPTION = ""
    BOOL_OP = OR
    TEST_MODE = Automatic
    PASSED -> GeometryReplacer
    FAILED -> Ugyldig_stedfesting
Note: Spatial is special! / Read coordinates from attribute / OGC well known text
GeometryReplacer
    SOURCE = @Value(wkt)
    REMOVE_ATTRIBUTE = No
    KIND_LONG = OGC Well Known Text
    -> AttributeRemover
AttributeRemover
    REMOVE_ATTRS = _creation_instance,_error,_http_status_code,_url_contents,_xml_feature_count_,_xml_feature_type_,_xml_source_,strekningslengde,vegobjektURI,antall,returnert,start
    LIST_ATTRS = _headers{} _headers{}.name _headers{}.value
    -> AttributeRemover_3
AttributeRemover_3
    REMOVE_ATTRS = href,objektTypeId,objektTypeNavn,sist_modifisert,srid,Veglenkeposisjon,wkt
    LIST_ATTRS = kontraktsomrade{} region{} riksvegrute{}
    -> ListExploder
    -> Bruer__multippel_stedfesting_
Bruer__multippel_stedfesting_: Inspector
ListExploder
    LIST_ATTR = segment{}
    ATTR_ACCUM_MODE = Merge Incoming List
    INDEX_ATTR = _element_index
    ATTR_CONFLICT_RES = Use Incoming List
    LIST_FOUND -> AttributeExposer
AttributeExposer
    ATTR_LIST = vegref,meter,frameter,tilmeter,fylke,hp,vegkategori,kommune,vegnummer,vegstatus,veglenkeid,posisjon,stedfesting,retning,fra_posisjon,til_posisjon,sideposisjon,segment_strekningslengde,wkt
    -> GeometryReplacer_2
GeometryReplacer_2
    SOURCE = @Value(wkt)
    REMOVE_ATTRIBUTE = No
    KIND_LONG = OGC Well Known Text
    -> LengthCalculator_2
LengthCalculator_2
    DIM = 2
    MULT = 1
    LEN_ATTR = geometriLengde
    -> AttributeRemover_2
AttributeRemover_2
    REMOVE_ATTRS = _element_index,egengeometri,href,meter,posisjon,segment,wkt
    LIST_ATTRS = kontraktsomrade{} region{} riksvegrute{}
    -> Segmenterte_bruer
Segmenterte_bruer: Inspector
Ugyldig_stedfesting: Inspector

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    ERROR_ATTR = _error
    VERIFY_SSL_CERTIFICATES = Yes
    USE_COOKIES = No
    STATUS_CODE_ATTR = _http_status_code
    REQUEST_HEADER:
      Accept:application/vnd.vegvesen.nvdb-v2+xml
      X-Client:FME http caller
      X-Kontaktperson: Jan Kristian Jensen
    FOLLOW_REDIRECTS = Yes
    SAVE_FILE = No
    PROXY_AUTH_METHOD = Basic
    TARGET_URL = @Value(vegobjektURI)
    AUTH_METHOD = Basic
    RESPONSE_HEADER_LIST_ATTR = _headers
    TARGET_ATTR = _url_contents
    -> XMLFeatureMapper_3
    <REJECTED> -> HTTPFetcher__Rejected_
XMLFeatureMapper_3
    XML_SOURCE_NAME = _xml_source_
    ATTRIBUTE_XML = _url_contents
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    MERGE_ATTRS = Yes
    CONFIGURATION_TYPE = Embedded xfMap script
    FEATURE_COUNT_PER_XML = _xml_feature_count_
    NEW_ATTRIBUTES = antall returnert start href
    XML_INPUT_TYPE = Attribute with XML document
    FEATURE_TYPE_ATTR = _xml_feature_type_
    MAPPED -> Tester
Tester
    TEST_CLAUSE = TEST @Value(returnert) > 0
    TEST_DESCRIPTION = ""
    BOOL_OP = OR
    TEST_MODE = Automatic
    PASSED -> Tester_Passed (output)
    FAILED -> Tester_Failed (output)
    PASSED -> AttributeCreator_4
