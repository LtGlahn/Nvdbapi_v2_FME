FME workspace sammenlign_BK.fmw

Parameters:
- apiFetchObjectURL = https://www.vegvesen.no/nvdb/api/v2/vegobjekter/   # URL to NVDB api /vegobjekter end point (v2)
- objektTypeID = 904   # ID of object type from NVDB api
- antall = 1000   # Antall objekter per iterasjon (maks 1000)
- DestDataset_GEOPACKAGE = C:\DATA\leveranser\diverse\bruksklasse_differanser.gpkg   # GeoPackage File
- DestDataset_GEOPACKAGE_3 = C:\DATA\leveranser\diverse\bruksklasser_identisk.gpkg   # GeoPackage File

Writers:
- GEOPACKAGE_1: GEOPACKAGE to $(DestDataset_GEOPACKAGE)
- GEOPACKAGE_2: GEOPACKAGE to $(DestDataset_GEOPACKAGE_3)

Creator
    GEOMTYPE = Geometry Object
    NUM = 1
    CREATED -> AttributeCreator_3
AttributeCreator_3
    ATTR_LIST = omradefilter,
    -> AttributeCreator
    -> AttributeCreator_5
    -> AttributeCreator_8
Note: 904 BK normaltransport
AttributeCreator
    ATTR_LIST = vegobjektURI,$(apiFetchObjectURL)904?inkluder=alle&srid=32633&antall=$(antall)
    -> AttributeCreator_4
Note: Føyer til filter
AttributeCreator_4
    ATTR_LIST = vegobjektURI,@Value(vegobjektURI)&@Value(omradefilter)
    -> loop_fetchdata [HTTPFetcher_Input]
loop_fetchdata
    VEGOBJEKTURI = @Value(vegobjektURI)
    Tester_Passed -> AttributeCreator_2
    Tester_Failed -> DONE
DONE: Inspector [off]
Note: AttributeCreator_2 [AttributeCreator] / Attributes To Set: Attribute NameValueBruksklasse<not set>Bruksklasse vinter<not set>Maks vogntoglengde<not set>Strekningsbeskrivelse<not set>Maks totalvekt kjøretøy, skiltet<not set>Maks totalvekt vogntog, skiltet<not set>Merknad<not set>
AttributeCreator_2
    ATTR_LIST = Bruksklasse,,Bruksklasse vinter,,Maks vogntoglengde,,Strekningsbeskrivelse,,Maks totalvekt kjøretøy, skiltet,,Maks totalvekt vogntog, skiltet,,Merknad,
    -> XMLFeatureMapper_3
XMLFeatureMapper_3
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = sist_modifisert id objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_5
Tester_5
    BOOL_OP = OR
    TEST_CLAUSE = TEST wkt NOT_ATTRIBUTE_IS_MISSING ""
    PASSED -> AttributeRemover
    FAILED -> Ugyldig_stedfesting
BulkAttributeRenamer_7
    ATTRCHOICE = All Attributes
    MODE_CHOICE = RENAME
    PATTERN_ACTION_DISP = ADDPREFIX
    REPLACE_STR = bknorm_
    -> BK_orginal
    -> InlineQuerier [bknorm]
Ugyldig_stedfesting: Inspector [off]
Note: 904 BK tømmertransport
AttributeCreator_5
    ATTR_LIST = vegobjektURI,$(apiFetchObjectURL)900?inkluder=alle&srid=32633&antall=$(antall)
    -> AttributeCreator_6
Note: Føyer til filter
AttributeCreator_6
    ATTR_LIST = vegobjektURI,@Value(vegobjektURI)&@Value(omradefilter)
    -> loop_fetchdata_2 [HTTPFetcher_Input]
loop_fetchdata_2
    VEGOBJEKTURI = @Value(vegobjektURI)
    Tester_Passed -> AttributeCreator_7
Note: AttributeCreator_7 [AttributeCreator] / Attributes To Set: Attribute NameValueBruksklasse<not set>Bruksklasse vinter<not set>Maks vogntoglengde<not set>Strekningsbeskrivelse<not set>Maks totalvekt kjøretøy, skiltet<not set>Maks totalvekt vogntog, skiltet<not set>Merknad<not set>
AttributeCreator_7
    ATTR_LIST = Bruksklasse,,Bruksklasse vinter,,Maks vogntoglengde,,Strekningsbeskrivelse,,Maks totalvekt kjøretøy, skiltet,,Maks totalvekt vogntog, skiltet,,Merknad,
    -> XMLFeatureMapper_2
XMLFeatureMapper_2
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = sist_modifisert id objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_2
Tester_2
    BOOL_OP = OR
    TEST_CLAUSE = TEST wkt NOT_ATTRIBUTE_IS_MISSING ""
    PASSED -> AttributeRemover_4
    FAILED -> Ugyldig_stedfesting_2
BK_tømmer_orginal: Inspector [off]
Ugyldig_stedfesting_2: Inspector [off]
Note: 902 BK spesialtransport
AttributeCreator_8
    ATTR_LIST = vegobjektURI,$(apiFetchObjectURL)902?inkluder=alle&srid=32633&antall=$(antall)
    -> AttributeCreator_9
Note: Føyer til filter
AttributeCreator_9
    ATTR_LIST = vegobjektURI,@Value(vegobjektURI)&@Value(omradefilter)
    -> loop_fetchdata_3 [HTTPFetcher_Input]
loop_fetchdata_3
    VEGOBJEKTURI = @Value(vegobjektURI)
    Tester_Passed -> AttributeCreator_10
Note: AttributeCreator_10 [AttributeCreator] / Attributes To Set: Attribute NameValueBruksklasse<not set>Bruksklasse vinter<not set>Maks vogntoglengde<not set>Veggruppe<not set>Strekningsbeskrivelse<not set>Merknad<not set>
AttributeCreator_10
    ATTR_LIST = Bruksklasse,,Bruksklasse vinter,,Maks vogntoglengde,,Veggruppe,,Strekningsbeskrivelse,,Merknad,
    -> XMLFeatureMapper_4
XMLFeatureMapper_4
    ATTRIBUTE_XML = _url_contents
    CONFIGURATION_TYPE = Single xfMap file
    FEATURE_COUNT_PER_XML = _xml_feature_count_
    FEATURE_TYPE_ATTR = _xml_feature_type_
    MERGE_ATTRS = No
    NEW_ATTRIBUTES = sist_modifisert id objektTypeId objektTypeNavn region{} kontraktsomrade{} riksvegrute{} wkt srid egengeometri strekningslengde segment{}
    SINGLE_XFMAP = $(FME_MF_DIR)xfmapDefintion_nvdbapi2fme_V2.xml
    XML_INPUT_TYPE = Attribute with XML document
    XML_SOURCE_NAME = _xml_source_
    MAPPED -> Tester_3
Tester_3
    BOOL_OP = OR
    TEST_CLAUSE = TEST wkt NOT_ATTRIBUTE_IS_MISSING ""
    PASSED -> AttributeRemover_7
    FAILED -> Ugyldig_stedfesting_3
jointommer: Inspector [off]
Joinspesial: Inspector [off]
identisk_normal_tommer (writer GEOPACKAGE_2)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
identisk_normal_spesial (writer GEOPACKAGE_2)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
BK_spesial_orginal: Inspector [off]
Ugyldig_stedfesting_3: Inspector [off]

Bookmark: Split object into individual road segments
AttributeRemover
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_3
AttributeRemover_3
    LIST_ATTRS = kontraktsomrade{} region{} riksvegrute{}
    REMOVE_ATTRS = href,objektTypeId,objektTypeNavn,sist_modifisert,srid,Veglenkeposisjon,wkt
    -> ListExploder
ListExploder
    ATTR_ACCUM_MODE = Merge Incoming List
    ATTR_CONFLICT_RES = Use Incoming List
    INDEX_ATTR = _element_index
    LIST_ATTR = segment{}
    LIST_FOUND -> AttributeExposer
    NOT_FOUND -> ListExploder_NotFound
AttributeExposer
    ATTR_LIST = vegref,meter,frameter,tilmeter,fylke,hp,vegkategori,kommune,vegnummer,vegstatus,veglenkeid,wkt,fra_posisjon,til_posisjon,stedfesting
    -> CoordinateSystemSetter
CoordinateSystemSetter
    COORDSYS = EPSG:25833
    -> GeometryReplacer_2
GeometryReplacer_2
    KIND_LONG = OGC Well Known Text
    REMOVE_ATTRIBUTE = Yes
    SOURCE = @Value(wkt)
    -> AttributeRemover_2
AttributeRemover_2
    REMOVE_ATTRS = meter,wkt,_element_index,egengeometri,segment
    -> BulkAttributeRenamer
LengthCalculator
    DIM = 2
    LEN_ATTR = lengde
    MULT = 1
    -> NullAttributeMapper_3
NullAttributeMapper_3
    ATTRCHOICE = Selected Attributes
    ATTRLIST = Maksvogntoglengde Makstotalvektvogntogskiltet Merknad Makstotalvektkjoretoyskiltet Strekningsbeskrivelse Bruksklasse Bruksklassevinter
    NULL_TREATMENT = Empty String
    SOURCE_ATTR_VAL = Empty Null "Missing (Selected Attributes Only)"
    -> AttributeRounder_2
AttributeRounder_2
    PLACES = 8
    ROUND_TYPE = Nearest
    SRC_ATTRS = fra_posisjon til_posisjon
    -> AttributeRenamer_2
AttributeRenamer_2
    ATTR_TABLE = RENAME_SET_DEFAULT id > nvdbid
    -> GeometryFilter_3
GeometryFilter_3
    BREAK_AGG = No
    GEOM_PORT_NAMES = Point Line
    POINT -> GeometryFilter_Point_3
    LINE -> BulkAttributeRenamer_7
    <UNFILTERED> -> GeometryFilter__Unfiltered__3
GeometryFilter_Point_3: Inspector
GeometryFilter__Unfiltered__3: Inspector
ListExploder_NotFound: Inspector

Bookmark: Pene egenskapnavn
BulkAttributeRenamer
    ATTRCHOICE = All Attributes
    MODE_CHOICE = RENAME
    PATTERN_ACTION_DISP = PCREGEXPREPLACE
    REPLACE_PATTERN = " "
    -> BulkAttributeRenamer_2
BulkAttributeRenamer_2
    ATTRCHOICE = All Attributes
    MODE_CHOICE = RENAME
    PATTERN_ACTION_DISP = PCREGEXPREPLACE
    REPLACE_PATTERN = ,
    -> BulkAttributeRenamer_3
BulkAttributeRenamer_3
    ATTRCHOICE = All Attributes
    MODE_CHOICE = RENAME
    PATTERN_ACTION_DISP = PCREGEXPREPLACE
    REPLACE_PATTERN = ø
    REPLACE_STR = o
    -> LengthCalculator

Bookmark: New Bookmark
BK_orginal: Inspector [off]
InlineQuerier
    QUERY_DEF:
      jon,select * from bknorm
          INNER JOIN tommerbk ON
            bknorm.bknorm_veglenkeid                 = tommerbk.veglenkeid   AND
            bknorm.bknorm_fra_posisjon              < tommerbk.til_posisjon  AND
            bknorm.bknorm_til_posisjon              > tommerbk.fra_posisjon  AND

          ( bknorm.bknorm_Bruksklasse                  != tommerbk.Bruksklasse OR
            bknorm.bknorm_Bruksklassevinter            != tommerbk.Bruksklassevinter OR
            bknorm.bknorm_Maksvogntoglengde            != tommerbk.Maksvogntoglengde OR
            bknorm.bknorm_Strekningsbeskrivelse        != tommerbk.Strekningsbeskrivelse OR
            bknorm.bknorm_Merknad                      != tommerbk.Merknad )
          ,FIRST,joinspesial,select * from bknorm
          INNER JOIN spesialbk ON
            bknorm.bknorm_veglenkeid                 = spesialbk.veglenkeid   AND
            bknorm.bknorm_fra_posisjon              < spesialbk.til_posisjon  AND
            bknorm.bknorm_til_posisjon              > spesialbk.fra_posisjon  AND

          ( bknorm.bknorm_Bruksklasse                  != spesialbk.Bruksklasse OR
            bknorm.bknorm_Bruksklassevinter            != spesialbk.Bruksklassevinter OR
            bknorm.bknorm_Maksvogntoglengde            != spesialbk.Maksvogntoglengde OR
            bknorm.bknorm_Strekningsbeskrivelse        != spesialbk.Strekningsbeskrivelse OR
            bknorm.bknorm_Merknad                      != spesialbk.Merknad )
          ,FIRST,identisk_tommer,select * from bknorm
          INNER JOIN tommerbk ON
            bknorm.bknorm_veglenkeid                 = tommerbk.veglenkeid   AND
            bknorm.bknorm_fra_posisjon              < tommerbk.til_posisjon  AND
            bknorm.bknorm_til_posisjon              > tommerbk.fra_posisjon  -- AND
      --
      --    ( bknorm.bknorm_Bruksklasse                  = tommerbk.Bruksklasse OR
      --      bknorm.bknorm_Bruksklassevinter            = tommerbk.Bruksklassevinter OR
      --      bknorm.bknorm_Maksvogntoglengde            = tommerbk.Maksvogntoglengde OR
      --     bknorm.bknorm_Strekningsbeskrivelse        = tommerbk.Strekningsbeskrivelse OR
      --      bknorm.bknorm_Merknad                      = tommerbk.Merknad )
          ,FIRST,identisk_spesial,select * from bknorm
          INNER JOIN spesialbk ON
            bknorm.bknorm_veglenkeid                 = spesialbk.veglenkeid   AND
            bknorm.bknorm_fra_posisjon              < spesialbk.til_posisjon  AND
            bknorm.bknorm_til_posisjon              > spesialbk.fra_posisjon -- AND
      --
      --    ( bknorm.bknorm_Bruksklasse                  = spesialbk.Bruksklasse OR
      --      bknorm.bknorm_Bruksklassevinter            = spesialbk.Bruksklassevinter OR
      --      bknorm.bknorm_Maksvogntoglengde            = spesialbk.Maksvogntoglengde OR
      --      bknorm.bknorm_Strekningsbeskrivelse        = spesialbk.Strekningsbeskrivelse OR
      --      bknorm.bknorm_Merknad                      = spesialbk.Merknad )
          ,FIRST,identisk_tommer_backup,select * from bknorm
          INNER JOIN tommerbk ON
            bknorm.bknorm_veglenkeid                 = tommerbk.veglenkeid   AND
            bknorm.bknorm_fra_posisjon              < tommerbk.til_posisjon  AND
            bknorm.bknorm_til_posisjon              > tommerbk.fra_posisjon  AND

          ( bknorm.bknorm_Bruksklasse                  = tommerbk.Bruksklasse OR
            bknorm.bknorm_Bruksklassevinter            = tommerbk.Bruksklassevinter OR
            bknorm.bknorm_Maksvogntoglengde            = tommerbk.Maksvogntoglengde OR
            bknorm.bknorm_Strekningsbeskrivelse        = tommerbk.Strekningsbeskrivelse OR
            bknorm.bknorm_Merknad                      = tommerbk.Merknad )
          ,FIRST,identisk_spesial_backup,select * from bknorm
          INNER JOIN spesialbk ON
            bknorm.bknorm_veglenkeid                 = spesialbk.veglenkeid   AND
            bknorm.bknorm_fra_posisjon              < spesialbk.til_posisjon  AND
            bknorm.bknorm_til_posisjon              > spesialbk.fra_posisjon  AND

          ( bknorm.bknorm_Bruksklasse                  = spesialbk.Bruksklasse OR
            bknorm.bknorm_Bruksklassevinter            = spesialbk.Bruksklassevinter OR
            bknorm.bknorm_Maksvogntoglengde            = spesialbk.Maksvogntoglengde OR
            bknorm.bknorm_Strekningsbeskrivelse        = spesialbk.Strekningsbeskrivelse OR
            bknorm.bknorm_Merknad                      = spesialbk.Merknad )
          ,FIRST
    QUERY_SCHEMA = jon,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Makstotalvektkjoretoyskiltet,varchar(200),Makstotalvektvogntogskiltet,varchar(200),Merknad,varchar(200),veglenkeid,integer,fra_posisjon,float,til_posisjon,float,tommerbk.fme_feature_content,fme_feature_content,joinspesial,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Merknad,varchar(200),veglenkeid,integer,fra_posisjon,float,til_posisjon,float,spesialbk.fme_feature_content,fme_feature_content,identisk_tommer,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Makstotalvektkjoretoyskiltet,varchar(200),Makstotalvektvogntogskiltet,varchar(200),Merknad,varchar(200),veglenkeid,integer,fra_posisjon,float,til_posisjon,float,tommerbk.fme_feature_content,fme_feature_content,identisk_spesial,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Merknad,varchar(200),veglenkeid,integer,fra_posisjon,float,til_posisjon,float,spesialbk.fme_feature_content,fme_feature_content,identisk_tommer_backup,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Makstotalvektkjoretoyskiltet,varchar(200),Makstotalvektvogntogskiltet,varchar(200),Merknad,varchar(200),veglenkeid,integer,fra_posisjon,float,til_posisjon,float,tommerbk.fme_feature_content,fme_feature_content,identisk_spesial_backup,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,bknorm.fme_feature_content,fme_feature_content,Bruksklasse,varchar(200),Bruksklassevinter,varchar(200),Maksvogntoglengde,varchar(200),Strekningsbeskrivelse,varchar(200),Merknad,varchar(200),veglenkeid,integer,fra_posisjon,float,til_posisjon,float,spesialbk.fme_feature_content,fme_feature_content
    TABLE_DEF = bknorm,bknorm_Bruksklasse,varchar(200),bknorm_Bruksklassevinter,varchar(200),bknorm_Maksvogntoglengde,varchar(200),bknorm_Strekningsbeskrivelse,varchar(200),bknorm_Makstotalvektkjoretoyskiltet,varchar(200),bknorm_Makstotalvektvogntogskiltet,varchar(200),bknorm_Merknad,varchar(200),bknorm_veglenkeid,integer,bknorm_fra_posisjon,float,bknorm_til_posisjon,float,tommerbk,Bruksklasse,varchar(200),Bruksklassevinter,varchar(200),Maksvogntoglengde,varchar(200),Strekningsbeskrivelse,varchar(200),Makstotalvektkjoretoyskiltet,varchar(200),Makstotalvektvogntogskiltet,varchar(200),Merknad,varchar(200),veglenkeid,integer,fra_posisjon,float,til_posisjon,float,spesialbk,Bruksklasse,varchar(200),Bruksklassevinter,varchar(200),Maksvogntoglengde,varchar(200),Strekningsbeskrivelse,varchar(200),Merknad,varchar(200),veglenkeid,integer,fra_posisjon,float,til_posisjon,float
    jon -> TestFilter
    jon -> bknorm_bktommer_diff (writer GEOPACKAGE_1)
    jon -> jointommer
    joinspesial -> Joinspesial
    joinspesial -> TestFilter_8
    joinspesial -> bknorm_bkspesial_diff (writer GEOPACKAGE_1)
    identisk_tommer -> identisk_normal_tommer (writer GEOPACKAGE_2)
    identisk_spesial -> identisk_normal_spesial (writer GEOPACKAGE_2)
TestFilter
    DEFAULT_VALUE = <UNFILTERED>
    TEST_LIST = "BOOL_OP,OR,COMPOSITE_TEST,""""""<Unused>"""""",TEST_CLAUSE,TEST @Value(Bruksklasse) != @Value(bknorm_Bruksklasse)",bruksklasse
    bruksklasse -> TestFilter_2
    bruksklasse -> bruksklasse_norm_tommer (writer GEOPACKAGE_1)
    bruksklasse -> bruksklasse
    <UNFILTERED> -> TestFilter_2
bruksklasse_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
bruksklasse: Inspector
TestFilter_2
    DEFAULT_VALUE = <UNFILTERED>
    TEST_LIST = "BOOL_OP,OR,COMPOSITE_TEST,""""""<Unused>"""""",TEST_CLAUSE,TEST @Value(Bruksklassevinter) != @Value(bknorm_Bruksklassevinter)",bkvinter
    bkvinter -> bkvinter_norm_tommer (writer GEOPACKAGE_1)
    bkvinter -> bkVinter
    bkvinter -> TestFilter_3
    <UNFILTERED> -> TestFilter_3
bkvinter_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
bkVinter: Inspector
TestFilter_3
    DEFAULT_VALUE = <UNFILTERED>
    TEST_LIST = "BOOL_OP,OR,COMPOSITE_TEST,""""""<Unused>"""""",TEST_CLAUSE,TEST @Value(Maksvogntoglengde) != @Value(bknorm_Maksvogntoglengde)",Maksvogntoglengde
    Maksvogntoglengde -> maksvogntoglengde_norm_tommer (writer GEOPACKAGE_1)
    Maksvogntoglengde -> Maksvogntoglengde
    Maksvogntoglengde -> TestFilter_4
    <UNFILTERED> -> TestFilter_4
maksvogntoglengde_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
Maksvogntoglengde: Inspector
TestFilter_4
    DEFAULT_VALUE = <UNFILTERED>
    TEST_LIST = "BOOL_OP,OR,COMPOSITE_TEST,""""""<Unused>"""""",TEST_CLAUSE,TEST @Value(Strekningsbeskrivelse) != @Value(bknorm_Strekningsbeskrivelse)",Strekningsbeskrivelse
    Strekningsbeskrivelse -> strekningsbeskr_norm_tommer (writer GEOPACKAGE_1)
    Strekningsbeskrivelse -> Strekningsbeskrivelse
    Strekningsbeskrivelse -> TestFilter_5
    <UNFILTERED> -> TestFilter_5
strekningsbeskr_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
Strekningsbeskrivelse: Inspector
TestFilter_5
    DEFAULT_VALUE = <UNFILTERED>
    TEST_LIST = "BOOL_OP,OR,COMPOSITE_TEST,""""""<Unused>"""""",TEST_CLAUSE,TEST @Value(Makstotalvektkjoretoyskiltet) != @Value(bknorm_Makstotalvektkjoretoyskiltet)",Makstotalvektkjoretoyskiltet
    Makstotalvektkjoretoyskiltet -> makstotvekt_kjt_skiltet_norm_tommer (writer GEOPACKAGE_1)
    Makstotalvektkjoretoyskiltet -> Makstotalvektkjoretoyskiltet
    Makstotalvektkjoretoyskiltet -> TestFilter_6
    <UNFILTERED> -> TestFilter_6
makstotvekt_kjt_skiltet_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
Makstotalvektkjoretoyskiltet: Inspector
TestFilter_6
    DEFAULT_VALUE = <UNFILTERED>
    TEST_LIST = "BOOL_OP,OR,COMPOSITE_TEST,""""""<Unused>"""""",TEST_CLAUSE,TEST @Value(Makstotalvektvogntogskiltet) != @Value(bknorm_Makstotalvektvogntogskiltet)",Makstotalvektvongtogskiltet
    Makstotalvektvongtogskiltet -> TestFilter_7
    Makstotalvektvongtogskiltet -> makstotvekt_vongtog_skilt_norm_tommer (writer GEOPACKAGE_1)
    Makstotalvektvongtogskiltet -> TestFilter_6_Makstotalvektvongtogskiltet
    <UNFILTERED> -> TestFilter_7
makstotvekt_vongtog_skilt_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
TestFilter_6_Makstotalvektvongtogskiltet: Inspector
TestFilter_7
    DEFAULT_VALUE = <UNFILTERED>
    TEST_LIST = "BOOL_OP,OR,COMPOSITE_TEST,""""""<Unused>"""""",TEST_CLAUSE,TEST @Value(Merknad) != @Value(bknorm_Merknad)",Merknad
    Merknad -> merknad_norm_tommer (writer GEOPACKAGE_1)
    Merknad -> Merknad
    <UNFILTERED> -> TestFilter_7__Unfiltered_
merknad_norm_tommer (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)
Merknad: Inspector
TestFilter_7__Unfiltered_: Inspector [off]
bknorm_bktommer_diff (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Makstotalvektkjoretoyskiltet text(200), Makstotalvektvogntogskiltet text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200),
      bknorm_stedfesting text(200), bknorm_lengde text(200), nvdbid text(200), vegref text(200), frameter text(200), tilmeter text(200), fylke text(200), hp text(200), vegkategori text(200), kommune text(200), vegnummer text(200), vegstatus text(200), stedfesting text(200), lengde text(200)

Bookmark: Split object into individual road segments
AttributeRemover_4
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_5
AttributeRemover_5
    LIST_ATTRS = kontraktsomrade{} region{} riksvegrute{}
    REMOVE_ATTRS = href,objektTypeId,objektTypeNavn,sist_modifisert,srid,Veglenkeposisjon,wkt
    -> ListExploder_2
ListExploder_2
    ATTR_ACCUM_MODE = Merge Incoming List
    ATTR_CONFLICT_RES = Use Incoming List
    INDEX_ATTR = _element_index
    LIST_ATTR = segment{}
    LIST_FOUND -> AttributeExposer_2
    NOT_FOUND -> ListExploder_NotFound_2
AttributeExposer_2
    ATTR_LIST = vegref,meter,frameter,tilmeter,fylke,hp,vegkategori,kommune,vegnummer,vegstatus,veglenkeid,wkt,fra_posisjon,til_posisjon,stedfesting
    -> CoordinateSystemSetter_2
CoordinateSystemSetter_2
    COORDSYS = EPSG:25833
    -> GeometryReplacer_3
GeometryReplacer_3
    KIND_LONG = OGC Well Known Text
    REMOVE_ATTRIBUTE = Yes
    SOURCE = @Value(wkt)
    -> AttributeRemover_6
AttributeRemover_6
    REMOVE_ATTRS = meter,wkt,_element_index,egengeometri,segment
    -> BulkAttributeRenamer_4
LengthCalculator_2
    DIM = 2
    LEN_ATTR = lengde
    MULT = 1
    -> NullAttributeMapper_2
NullAttributeMapper_2
    ATTRCHOICE = Selected Attributes
    ATTRLIST = Maksvogntoglengde Makstotalvektvogntogskiltet Merknad Makstotalvektkjoretoyskiltet Strekningsbeskrivelse Bruksklasse Bruksklassevinter
    NULL_TREATMENT = Empty String
    SOURCE_ATTR_VAL = Empty Null "Missing (Selected Attributes Only)"
    -> AttributeRounder
AttributeRounder
    PLACES = 8
    ROUND_TYPE = Nearest
    SRC_ATTRS = fra_posisjon til_posisjon
    -> AttributeRenamer
AttributeRenamer
    ATTR_TABLE = RENAME_SET_DEFAULT id > nvdbid
    -> GeometryFilter_2
GeometryFilter_2
    BREAK_AGG = No
    GEOM_PORT_NAMES = Point Line
    POINT -> GeometryFilter_Point_2
    LINE -> InlineQuerier [tommerbk]
    <UNFILTERED> -> GeometryFilter__Unfiltered__2
GeometryFilter_Point_2: Inspector
GeometryFilter__Unfiltered__2: Inspector
ListExploder_NotFound_2: Inspector

Bookmark: Pene egenskapnavn
BulkAttributeRenamer_4
    ATTRCHOICE = All Attributes
    MODE_CHOICE = RENAME
    PATTERN_ACTION_DISP = PCREGEXPREPLACE
    REPLACE_PATTERN = " "
    -> BulkAttributeRenamer_5
BulkAttributeRenamer_5
    ATTRCHOICE = All Attributes
    MODE_CHOICE = RENAME
    PATTERN_ACTION_DISP = PCREGEXPREPLACE
    REPLACE_PATTERN = ,
    -> BulkAttributeRenamer_6
BulkAttributeRenamer_6
    ATTRCHOICE = All Attributes
    MODE_CHOICE = RENAME
    PATTERN_ACTION_DISP = PCREGEXPREPLACE
    REPLACE_PATTERN = ø
    REPLACE_STR = o
    -> BK_tømmer_orginal
    -> LengthCalculator_2

Bookmark: Split object into individual road segments
AttributeRemover_7
    LIST_ATTRS = _headers{} _headers{}.name _headers{}.value
    REMOVE_ATTRS = _creation_instance,_error,_http_status_code,_url_contents,_xml_feature_count_,_xml_feature_type_,_xml_source_,antall,returnert,start,strekningslengde,vegobjektURI,omradefilter
    -> AttributeRemover_8
AttributeRemover_8
    LIST_ATTRS = kontraktsomrade{} region{} riksvegrute{}
    REMOVE_ATTRS = href,objektTypeId,objektTypeNavn,sist_modifisert,srid,Veglenkeposisjon,wkt
    -> ListExploder_3
ListExploder_3
    ATTR_ACCUM_MODE = Merge Incoming List
    ATTR_CONFLICT_RES = Use Incoming List
    INDEX_ATTR = _element_index
    LIST_ATTR = segment{}
    LIST_FOUND -> AttributeExposer_3
    NOT_FOUND -> ListExploder_NotFound_3
AttributeExposer_3
    ATTR_LIST = vegref,meter,frameter,tilmeter,fylke,hp,vegkategori,kommune,vegnummer,vegstatus,veglenkeid,wkt,fra_posisjon,til_posisjon,stedfesting
    -> CoordinateSystemSetter_3
CoordinateSystemSetter_3
    COORDSYS = EPSG:25833
    -> GeometryReplacer_4
GeometryReplacer_4
    KIND_LONG = OGC Well Known Text
    REMOVE_ATTRIBUTE = Yes
    SOURCE = @Value(wkt)
    -> AttributeRemover_9
AttributeRemover_9
    REMOVE_ATTRS = meter,wkt,_element_index,egengeometri,segment
    -> BulkAttributeRenamer_8
LengthCalculator_3
    DIM = 2
    LEN_ATTR = lengde
    MULT = 1
    -> NullAttributeMapper_4
NullAttributeMapper_4
    ATTRCHOICE = Selected Attributes
    ATTRLIST = Maksvogntoglengde Merknad Strekningsbeskrivelse Bruksklasse Bruksklassevinter
    NULL_TREATMENT = Empty String
    SOURCE_ATTR_VAL = Empty Null "Missing (Selected Attributes Only)"
    -> AttributeRounder_3
AttributeRounder_3
    PLACES = 8
    ROUND_TYPE = Nearest
    SRC_ATTRS = fra_posisjon til_posisjon
    -> AttributeRenamer_3
AttributeRenamer_3
    ATTR_TABLE = RENAME_SET_DEFAULT id > nvdbid
    -> GeometryFilter
GeometryFilter
    BREAK_AGG = No
    GEOM_PORT_NAMES = Point Line
    POINT -> GeometryFilter_Point
    LINE -> InlineQuerier [spesialbk]
    <UNFILTERED> -> GeometryFilter__Unfiltered_
GeometryFilter_Point: Inspector
GeometryFilter__Unfiltered_: Inspector
ListExploder_NotFound_3: Inspector

Bookmark: Pene egenskapnavn
BulkAttributeRenamer_8
    ATTRCHOICE = All Attributes
    MODE_CHOICE = RENAME
    PATTERN_ACTION_DISP = PCREGEXPREPLACE
    REPLACE_PATTERN = " "
    -> BulkAttributeRenamer_9
BulkAttributeRenamer_9
    ATTRCHOICE = All Attributes
    MODE_CHOICE = RENAME
    PATTERN_ACTION_DISP = PCREGEXPREPLACE
    REPLACE_PATTERN = ,
    -> BulkAttributeRenamer_10
BulkAttributeRenamer_10
    ATTRCHOICE = All Attributes
    MODE_CHOICE = RENAME
    PATTERN_ACTION_DISP = PCREGEXPREPLACE
    REPLACE_PATTERN = ø
    REPLACE_STR = o
    -> BK_spesial_orginal
    -> LengthCalculator_3

Bookmark: New Bookmark
TestFilter_8
    DEFAULT_VALUE = <UNFILTERED>
    TEST_LIST = "BOOL_OP,OR,COMPOSITE_TEST,""""""<Unused>"""""",TEST_CLAUSE,TEST @Value(Bruksklasse) != @Value(bknorm_Bruksklasse)",bruksklasse
    bruksklasse -> TestFilter_9
    bruksklasse -> bruksklasse_norm_spesial (writer GEOPACKAGE_1)
    bruksklasse -> spesial_bruksklasse
    <UNFILTERED> -> TestFilter_9
bruksklasse_norm_spesial (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
spesial_bruksklasse: Inspector
TestFilter_9
    DEFAULT_VALUE = <UNFILTERED>
    TEST_LIST = "BOOL_OP,OR,COMPOSITE_TEST,""""""<Unused>"""""",TEST_CLAUSE,TEST @Value(Bruksklassevinter) != @Value(bknorm_Bruksklassevinter)",bkvinter
    bkvinter -> bkvinter_norm_spesial (writer GEOPACKAGE_1)
    bkvinter -> spesial_bkVinter
    bkvinter -> TestFilter_10
    <UNFILTERED> -> TestFilter_10
bkvinter_norm_spesial (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
spesial_bkVinter: Inspector
TestFilter_10
    DEFAULT_VALUE = <UNFILTERED>
    TEST_LIST = "BOOL_OP,OR,COMPOSITE_TEST,""""""<Unused>"""""",TEST_CLAUSE,TEST @Value(Maksvogntoglengde) != @Value(bknorm_Maksvogntoglengde)",Maksvogntoglengde
    Maksvogntoglengde -> maksvogntoglengde_norm_spesial (writer GEOPACKAGE_1)
    Maksvogntoglengde -> spesial_maksvogntoglengde
    Maksvogntoglengde -> TestFilter_11
    <UNFILTERED> -> TestFilter_11
maksvogntoglengde_norm_spesial (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
spesial_maksvogntoglengde: Inspector
TestFilter_11
    DEFAULT_VALUE = <UNFILTERED>
    TEST_LIST = "BOOL_OP,OR,COMPOSITE_TEST,""""""<Unused>"""""",TEST_CLAUSE,TEST @Value(Strekningsbeskrivelse) != @Value(bknorm_Strekningsbeskrivelse)",Strekningsbeskrivelse
    Strekningsbeskrivelse -> strekningsbeskr_norm_spesial (writer GEOPACKAGE_1)
    Strekningsbeskrivelse -> Spesial_Strekningsbeskrivelse
    Strekningsbeskrivelse -> TestFilter_14
    <UNFILTERED> -> TestFilter_14
strekningsbeskr_norm_spesial (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
Spesial_Strekningsbeskrivelse: Inspector
TestFilter_14
    DEFAULT_VALUE = <UNFILTERED>
    TEST_LIST = "BOOL_OP,OR,COMPOSITE_TEST,""""""<Unused>"""""",TEST_CLAUSE,TEST @Value(Merknad) != @Value(bknorm_Merknad)",Merknad
    Merknad -> merknad_norm_spesial (writer GEOPACKAGE_1)
    Merknad -> spesial_merknad
    <UNFILTERED> -> TestFilter_7__Unfiltered__2
merknad_norm_spesial (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)
spesial_merknad: Inspector
TestFilter_7__Unfiltered__2: Inspector [off]
bknorm_bkspesial_diff (writer GEOPACKAGE_1)
    attributes: bknorm_Bruksklasse text(200), bknorm_Bruksklassevinter text(200), bknorm_Maksvogntoglengde text(200), bknorm_Strekningsbeskrivelse text(200), bknorm_Makstotalvektkjoretoyskiltet text(200), bknorm_Makstotalvektvogntogskiltet text(200), bknorm_Merknad text(200), bknorm_veglenkeid text(200), bknorm_fra_posisjon text(200), bknorm_til_posisjon text(200), Bruksklasse text(200), Bruksklassevinter text(200), Maksvogntoglengde text(200), Strekningsbeskrivelse text(200), Merknad text(200), veglenkeid text(200), fra_posisjon text(200), til_posisjon text(200), bknorm_nvdbid text(200), bknorm_vegref text(200), bknorm_frameter text(200), bknorm_tilmeter text(200), bknorm_fylke text(200), bknorm_hp text(200), bknorm_vegkategori text(200), bknorm_kommune text(200), bknorm_vegnummer text(200), bknorm_vegstatus text(200), bknorm_stedfesting text(200), bknorm_lengde text(200),
      nvdbid text(200), Veggruppe text(200), vegref text(200), frameter text(200), tilmeter text(200), fylke text(200), hp text(200), vegkategori text(200), kommune text(200), vegnummer text(200), vegstatus text(200), stedfesting text(200), lengde text(200)

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    AUTH_METHOD = Basic
    ERROR_ATTR = _error
    FOLLOW_REDIRECTS = Yes
    PROXY_AUTH_METHOD = Basic
    REQUEST_HEADER:
      Accept:application/vnd.vegvesen.nvdb-v2+xml
      X-Client:FME http caller
      X-Kontaktperson: Jan Kristian Jensen
    RESPONSE_HEADER_LIST_ATTR = _headers
    SAVE_FILE = No
    STATUS_CODE_ATTR = _http_status_code
    TARGET_ATTR = _url_contents
    TARGET_URL = @Value(vegobjektURI)
    USE_COOKIES = No
    VERIFY_SSL_CERTIFICATES = Yes
    -> XMLFeatureMapper_3
    <REJECTED> -> HTTPFetcher__Rejected_
XMLFeatureMapper_3
    ATTRIBUTE_XML = _url_contents
    CONFIGURATION_TYPE = Embedded xfMap script
    FEATURE_COUNT_PER_XML = _xml_feature_count_
    FEATURE_TYPE_ATTR = _xml_feature_type_
    MERGE_ATTRS = Yes
    NEW_ATTRIBUTES = antall returnert start href
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    XML_INPUT_TYPE = Attribute with XML document
    XML_SOURCE_NAME = _xml_source_
    MAPPED -> Tester
Tester
    BOOL_OP = OR
    TEST_CLAUSE = TEST @Value(returnert) > 0
    PASSED -> Tester_Passed (output)
    PASSED -> AttributeCreator_4
    FAILED -> Tester_Failed (output)
