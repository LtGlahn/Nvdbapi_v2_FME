FME workspace nvdbapi_V2_trafikkulykker.fmw

Parameters:
- apiFetchObjectURL = https://www.vegvesen.no/nvdb/api/v2/vegobjekter/   # URL to NVDB api /vegobjekter end point (v2)
- objektTypeID = 570   # ID of object type from NVDB api
- antall = 1000   # Antall objekter per iterasjon (maks 1000)

Creator
    NUM = 1
    GEOMTYPE = Geometry Object
    CREATED -> AttributeCreator
AttributeCreator
    ATTR_LIST = vegobjektURI,$(apiFetchObjectURL)$(objektTypeID)?inkluder=alle&srid=32633&antall=$(antall)
    -> AttributeCreator_4
Note: Egenskapsfilter (property filter) Alvorligste skadegrad = drept / Føy til nøkkelord-parameter &egenskap="5074=6427" til lenken / Mulige verdier for skadegrad: / 5074=6427 Alvorligste skadegrad = Drept / 5074=6428 Alvorligste skadegrad = Meget alvorlig skadd / 5074=6429 Alvorligste skadegrad = Alvorlig skadd / 5074=6430 Alvorligste skadegrad = Lettere skadd / 5074=6431 Alvorligste skadegrad = Uskadd / 5074=11664 Alvorligste skadegrad = Ikke registrert
AttributeCreator_3
    ATTR_LIST = vegobjektURI,@Value(vegobjektURI)&egenskap="5074=6427"
    -> AttributeCreator_4
Note: Are filter (property filter) / Tromsø kommune / 1902
AttributeCreator_4
    ATTR_LIST = vegobjektURI,@Value(vegobjektURI)&kommune=1902
    -> loop_fetchdata
loop_fetchdata
    VEGOBJEKTURI = @Value(vegobjektURI)
    Tester_Failed -> DONE
    Tester_Passed -> AttributeCreator_2
DONE: Inspector [off]
Note: Explisit define the attributes! / Must be tuned to your object type definition! / (Just ignore the properties you don't need) / Alvorligste skadegrad / Ulykkesdato / ... and so on
AttributeCreator_2
    ATTR_LIST = Alvorligste skadegrad,"",Ulykkesdato,"",Ulykkestidspunkt,"",Ukedag,"",Registreringsdato for fagdata,"",Ulykke registrert av,"",Meldingsdato,"",Behandlende politidistrikt,"",Anmeldelsesnummer,"",Kilde for ulykken,"",Registrering status,"",Uhell kategori,"",Uhellskode,"",Alternativ uhellskode,"",Beskrivelse,"",Stedsbeskrivelse,"",Antall enheter,"",Antall drepte i ulykken,"",Antall meget alvorlig skadet,"",Antall alvorlig skadet,"",Antall lettere skadet,"",Oppgitt antall skadde,"",Vegtype,"",Stedsforhold,"",Midtdeler,"",Forsterket vegoppmerking,"",Dekketype,"",Føreforhold,"",Værforhold,"",Lysforhold,"",Felttype,"",Antall kjørefelt,"",Bebyggelse,"",Vegbredde,"",Fartsgrense,"",Temperatur,"",Ok SSB,"",Kommunenr,"",Historisk vegstatus,"",Historisk vegkategori,"",Historisk vegnummer,"",Historisk hp,"",Historisk kilometerverdi,"",Vegnavn,"",Stedfestingens nøyaktighet,""
    -> XMLFeatureMapper_3
Note: This is where the magic happens! / xml=>FME features
XMLFeatureMapper_3
    CONFIGURATION_TYPE = Single xfMap file
    ATTRIBUTE_XML = _url_contents
    XML_SOURCE_NAME = _xml_source_
    SINGLE_XFMAP = $(FME_MF_DIR)xfmapDefintion_nvdbapi2fme_V2.xml
    FEATURE_COUNT_PER_XML = _xml_feature_count_
    NEW_ATTRIBUTES = sist_modifisert id objektTypeId objektTypeNavn region{} kontraktsomrade{} riksvegrute{} wkt srid egengeometri strekningslengde segment{}
    XML_INPUT_TYPE = Attribute with XML document
    FEATURE_TYPE_ATTR = _xml_feature_type_
    MERGE_ATTRS = No
    MAPPED -> CoordinateSystemSetter
Note: Set coordinate system / EPSG:25833 / (Not 32633, error in NVDB api documentation)
CoordinateSystemSetter
    COORDSYS = EPSG:25833
    -> GeometryReplacer
Note: Spatial is special! / Read coordinates from attribute / OGC well known text
GeometryReplacer
    SOURCE = @Value(wkt)
    KIND_LONG = OGC Well Known Text
    REMOVE_ATTRIBUTE = No
    -> AttributeRemover
AttributeRemover
    REMOVE_ATTRS = _creation_instance,_error,_http_status_code,_url_contents,_xml_feature_count_,_xml_feature_type_,_xml_source_,strekningslengde,vegobjektURI,antall,returnert,start
    LIST_ATTRS = _headers{} _headers{}.name _headers{}.value
    -> PythonCaller
Note: Using pythonCaller to get data from list
PythonCaller
    PYTHONSOURCE:
      import fmeobjects
      import re
      import json


      def liste2egenskaper( feature ):

          vegref =  feature.getAttribute('segment{0}.vegref' )
          fylke =  feature.getAttribute('segment{0}.fylke' )
          veglenkeposisjon = float( feature.getAttribute('segment{0}.posisjon' ) )
          veglenkeid = feature.getAttribute('segment{0}.veglenkeid' )

          # BUG in NVDB api - won't return valid data at veglenkeID@posisjon
          # Workaround: Use veglenkeID@fromPos-toPos syntax
          delta = 0.00000001
          fra = veglenkeposisjon - delta
          til = veglenkeposisjon + delta

          if fra <= 0:
              fra = veglenkeposisjon
              til = fra + delta
          elif til >= 1:
              til = veglenkeposisjon
              fra = til - delta

          mystr = str( fra) + '-' + str( til ) + '@' + str( veglenkeid )

          kat = feature.getAttribute('segment{0}.vegkategori' )
          status = feature.getAttribute('segment{0}.vegstatus' )
          vegnr = feature.getAttribute('segment{0}.vegnummer' )

          mittvegnr = kat + status.lower() + vegnr

          feature.setAttribute("Vegreferanse", vegref)
          feature.setAttribute("Fylke", fylke)
          feature.setAttribute("Veglenkeposisjon", mystr)
          feature.setAttribute("Vegnr", mittvegnr)
    PYTHONSYMBOL = liste2egenskaper
    NEW_ATTRIBUTES = Vegreferanse Veglenkeposisjon Fylke Vegnr
    -> AttributeRemover_3
AttributeRemover_3
    REMOVE_ATTRS = _error,_http_status_code,_url_contents,_xml_feature_count_,_xml_feature_type_,_xml_source_,Geometri, punkt,href,objektTypeId,objektTypeNavn,sist_modifisert,srid,Veglenkeposisjon,vegobjektURI,wkt
    LIST_ATTRS = _headers{} _headers{}.name _headers{}.value kontraktsomrade{} region{} riksvegrute{} segment{}
    -> Trafikkulykker
Trafikkulykker: Inspector

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    AUTH_METHOD = Basic
    ERROR_ATTR = _error
    TARGET_ATTR = _url_contents
    STATUS_CODE_ATTR = _http_status_code
    FOLLOW_REDIRECTS = Yes
    PROXY_AUTH_METHOD = Basic
    SAVE_FILE = No
    TARGET_URL = @Value(vegobjektURI)
    USE_COOKIES = No
    RESPONSE_HEADER_LIST_ATTR = _headers
    VERIFY_SSL_CERTIFICATES = Yes
    REQUEST_HEADER:
      Accept:application/vnd.vegvesen.nvdb-v2+xml
      X-Client:FME http caller
      X-Kontaktperson: Jan Kristian Jensen
    -> XMLFeatureMapper_3
    <REJECTED> -> HTTPFetcher__Rejected_
XMLFeatureMapper_3
    CONFIGURATION_TYPE = Embedded xfMap script
    ATTRIBUTE_XML = _url_contents
    XML_SOURCE_NAME = _xml_source_
    FEATURE_COUNT_PER_XML = _xml_feature_count_
    NEW_ATTRIBUTES = antall returnert start href
    XML_INPUT_TYPE = Attribute with XML document
    FEATURE_TYPE_ATTR = _xml_feature_type_
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    MERGE_ATTRS = Yes
    MAPPED -> Tester
Tester
    TEST_DESCRIPTION = ""
    TEST_CLAUSE = TEST @Value(returnert) > 0
    TEST_MODE = Automatic
    BOOL_OP = OR
    PASSED -> Tester_Passed (output)
    FAILED -> Tester_Failed (output)
    PASSED -> AttributeCreator_4
