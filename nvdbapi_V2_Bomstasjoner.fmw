FME workspace nvdbapi_V2_Bomstasjoner.fmw

Parameters:
- apiFetchObjectURL = https://www.vegvesen.no/nvdb/api/v2/vegobjekter/   # URL to NVDB api /vegobjekter end point (v2)
- objektTypeID = 45   # ID of object type from NVDB api
- antall = 1000   # Antall objekter per iterasjon (maks 1000)

Creator
    NUM = 1
    GEOMTYPE = Geometry Object
    CREATED -> AttributeCreator
AttributeCreator
    ATTR_LIST = vegobjektURI,$(apiFetchObjectURL)$(objektTypeID)?inkluder=alle&srid=32633&antall=$(antall)
    -> loop_fetchdata [HTTPFetcher_Input]
    -> AttributeCreator_3 [off]
Note: Egenskapsfilter (property filter) / Toll (takst) >= 20 kr
AttributeCreator_3
    ATTR_LIST = vegobjektURI,@Value(vegobjektURI)&egenskap="1820>=20"
    -> AttributeCreator_4
Note: Are filter (property filter) / Region=3
AttributeCreator_4
    ATTR_LIST = vegobjektURI,@Value(vegobjektURI)&region=3
    -> loop_fetchdata [HTTPFetcher_Input]
loop_fetchdata
    VEGOBJEKTURI = @Value(vegobjektURI)
    Tester_Passed -> AttributeCreator_2
    Tester_Failed -> DONE
Note: explisit define your attributes
DONE: Inspector [off]
Note: Explisit define the attributes! / Must be tuned to your object type definition! / (Just ignore the properties you don't need) / Takst liten bil = / Takst stor bil = / Bomstasjonstype = / Navn bomstasjon = / ... and so on
AttributeCreator_2
    ATTR_LIST = Takst liten bil,"",Takst stor bil,"",Bomstasjonstype,"",Navn bomstasjon,"",Utgår_Navn bompengeanlegg,"",Navn bompengeanlegg (fra CS),"",Vedtatt til år,"",Link til bomstasjon,"",Innkrevningsretning,"",Bomstasjon_Id,"",Bompengeanlegg_Id,"",Tidsdifferensiert takst,"",Rushtidstakst liten bil,"",Rushtidstakst stor bil,"",Rushtid morgen, fra,"",Rushtid morgen, til,"",Rushtid ettermiddag, fra,"",Rushtid ettermiddag, til,"",Timesregel,"",Gratis gjennomkjøring ved HC-brikke,"",Etableringsår,"",Eier,"",Vedlikeholdsansvarlig,"",Geometri, punkt,""
    -> XMLFeatureMapper_3
Note: This is where the magic happens! / xml=>FME features
XMLFeatureMapper_3
    FEATURE_TYPE_ATTR = _xml_feature_type_
    FEATURE_COUNT_PER_XML = _xml_feature_count_
    CONFIGURATION_TYPE = Single xfMap file
    MERGE_ATTRS = No
    NEW_ATTRIBUTES = sist_modifisert id objektTypeId objektTypeNavn region{} kontraktsomrade{} riksvegrute{} wkt srid egengeometri strekningslengde segment{} lokasjon{}
    XML_INPUT_TYPE = Attribute with XML document
    ATTRIBUTE_XML = _url_contents
    XML_SOURCE_NAME = _xml_source_
    SINGLE_XFMAP = $(FME_MF_DIR)xfmapDefintion_nvdbapi2fme_V2.xml
    MAPPED -> CoordinateSystemSetter
Note: Set coordinate system / EPSG:25833 / (Not 32633, error in NVDB api documentation)
CoordinateSystemSetter
    COORDSYS = EPSG:25833
    -> GeometryReplacer
Note: Spatial is special! / Read coordinates from attribute / OGC well known text
GeometryReplacer
    SOURCE = @Value(wkt)
    REMOVE_ATTRIBUTE = No
    KIND_LONG = OGC Well Known Text
    -> AttributeRemover
AttributeRemover
    REMOVE_ATTRS = _creation_instance,_error,_http_status_code,_url_contents,_xml_feature_count_,_xml_feature_type_,_xml_source_,strekningslengde,vegobjektURI,antall,returnert,start
    LIST_ATTRS = _headers{} _headers{}.name _headers{}.value
    -> PythonCaller
Note: Activate this to get street names / (kinda slow, one http get per feature)
Note: Using pythonCaller to get data from list
PythonCaller
    NEW_ATTRIBUTES = Vegreferanse Veglenkeposisjon Fylke Vegnr
    PYTHONSYMBOL = liste2egenskaper
    PYTHONSOURCE:
      import fmeobjects
      import re
      import json


      def liste2egenskaper( feature ):

          vegref =  feature.getAttribute('segment{0}.vegref' )
          fylke =  feature.getAttribute('segment{0}.fylke' )
          veglenkeposisjon = float( feature.getAttribute('segment{0}.posisjon' ) )
          veglenkeid = feature.getAttribute('segment{0}.veglenkeid' )

          # BUG in NVDB api - won't return valid data at veglenkeID@posisjon
          # Workaround: Use veglenkeID@fromPos-toPos syntax
          delta = 0.00000001
          fra = veglenkeposisjon - delta
          til = veglenkeposisjon + delta

          if fra <= 0:
              fra = veglenkeposisjon
              til = fra + delta
          elif til >= 1:
              til = veglenkeposisjon
              fra = til - delta

          mystr = str( fra) + '-' + str( til ) + '@' + str( veglenkeid )

          kat = feature.getAttribute('segment{0}.vegkategori' )
          status = feature.getAttribute('segment{0}.vegstatus' )
          vegnr = feature.getAttribute('segment{0}.vegnummer' )

          mittvegnr = kat + status.lower() + str(vegnr)

          feature.setAttribute("Vegreferanse", vegref)
          feature.setAttribute("Fylke", fylke)
          feature.setAttribute("Veglenkeposisjon", mystr)
          feature.setAttribute("Vegnr", mittvegnr)
    -> AttributeRenamer [off]
    -> AttributeRemover_3
Bomstasjoner___gatenavn: Inspector
AttributeRemover_3
    REMOVE_ATTRS = _error,_http_status_code,_url_contents,_xml_feature_count_,_xml_feature_type_,_xml_source_,Geometri, punkt,href,objektTypeId,objektTypeNavn,sist_modifisert,srid,Veglenkeposisjon,vegobjektURI,wkt
    LIST_ATTRS = _headers{} _headers{}.name _headers{}.value kontraktsomrade{} region{} riksvegrute{} segment{}
    -> Bomstasjoner
Note: Technically, we're done now!
Bomstasjoner: Inspector

Bookmark: Get street name from "Gate" object (optional)
Note: Renaming ID of bomstasjon => NVDB id / To avoid name clash with gate - object
AttributeRenamer
    ATTR_LIST = id,NVDB ID,
    -> AttributeCreator_7
Note: URL to get gate at the same road link position / as bomstasjon
AttributeCreator_7
    ATTR_LIST = vegobjektURI,$(apiFetchObjectURL)538?inkluder=egenskaper&veglenke=@Value(Veglenkeposisjon)
    -> HTTPFetcher
Note: Download XML data from NVDB api
HTTPFetcher
    STATUS_CODE_ATTR = _http_status_code
    RESPONSE_HEADER_LIST_ATTR = _headers
    TARGET_URL = @Value(vegobjektURI)
    AUTH_METHOD = Basic
    TARGET_ATTR = _url_contents
    PROXY_AUTH_METHOD = Basic
    REQUEST_HEADER:
      Accept:application/vnd.vegvesen.nvdb-v2+xml
      X-Client:FME http caller
      X-Kontaktperson: Jan Kristian Jensen
    ERROR_ATTR = _error
    FOLLOW_REDIRECTS = Yes
    SAVE_FILE = No
    USE_COOKIES = No
    VERIFY_SSL_CERTIFICATES = Yes
    -> XMLFeatureMapper_2
    -> FeatureMerger [REQUESTOR]
Note: This is where the magic happens! / xml=>FME features
XMLFeatureMapper_2
    FEATURE_TYPE_ATTR = _xml_feature_type_
    FEATURE_COUNT_PER_XML = _xml_feature_count_
    CONFIGURATION_TYPE = Single xfMap file
    MERGE_ATTRS = Yes
    NEW_ATTRIBUTES = Gatenavn
    XML_INPUT_TYPE = Attribute with XML document
    ATTRIBUTE_XML = _url_contents
    XML_SOURCE_NAME = _xml_source_
    SINGLE_XFMAP = $(FME_MF_DIR)xfmapDefintion_nvdbapi2fme_V2.xml
    MAPPED -> FeatureMerger [SUPPLIER]
    INVALID -> XMLFeatureMapper_2_Invalid
FeatureMerger
    SUPPLIERS_FIRST = No
    IGNORE_NULLS = No
    ATTR_CONFLICT_RES = Use Requestor
    ATTR_ACCUM_MODE = Merge Supplier
    MERGE_TYPE = Attributes Only
    PROCESS_DUPS = No
    JOIN_KEYS = @Value(NVDB ID) @Value(NVDB ID) AUTO
    MERGED -> AttributeRemover_2
    NOT_MERGED -> AttributeRemover_2
AttributeRemover_2
    REMOVE_ATTRS = _error,_http_status_code,_url_contents,_xml_feature_count_,_xml_feature_type_,_xml_source_,Geometri, punkt,href,objektTypeId,objektTypeNavn,sist_modifisert,srid,Veglenkeposisjon,vegobjektURI,wkt
    LIST_ATTRS = _headers{} _headers{}.name _headers{}.value kontraktsomrade{} region{} riksvegrute{} segment{}
    -> Bomstasjoner___gatenavn
XMLFeatureMapper_2_Invalid: Inspector

FME custom transformer loop_fetchdata

Parameters:
- VEGOBJEKTURI = @Value(vegobjektURI)   # vegobjektURI

HTTPFetcher_Input (input)
    -> HTTPFetcher
HTTPFetcher__Rejected_: Inspector
Note: New download URL / (next page in pagination)
AttributeCreator_4
    ATTR_LIST = vegobjektURI,@Value(href)
    -> HTTPFetcher_Input (output)
HTTPFetcher_Input (output)
Tester_Passed (output)
Tester_Failed (output)

Bookmark: loop_fetchdata
Note: Download XML data from NVDB api
HTTPFetcher
    STATUS_CODE_ATTR = _http_status_code
    RESPONSE_HEADER_LIST_ATTR = _headers
    TARGET_URL = @Value(vegobjektURI)
    AUTH_METHOD = Basic
    TARGET_ATTR = _url_contents
    PROXY_AUTH_METHOD = Basic
    REQUEST_HEADER:
      Accept:application/vnd.vegvesen.nvdb-v2+xml
      X-Client:FME http caller
      X-Kontaktperson: Jan Kristian Jensen
    ERROR_ATTR = _error
    FOLLOW_REDIRECTS = Yes
    SAVE_FILE = No
    USE_COOKIES = No
    VERIFY_SSL_CERTIFICATES = Yes
    -> XMLFeatureMapper_3
    <REJECTED> -> HTTPFetcher__Rejected_
XMLFeatureMapper_3
    FEATURE_TYPE_ATTR = _xml_feature_type_
    FEATURE_COUNT_PER_XML = _xml_feature_count_
    CONFIGURATION_TYPE = Embedded xfMap script
    MERGE_ATTRS = Yes
    NEW_ATTRIBUTES = antall returnert start href
    SCRIPT_XFMAP:
      <?xml version="1.0"?>
      <xfMap>
       <feature-map multi-feature-construction="true">
          <mapping match="side/metadata">
             <feature-type> <literal expr="metadata"/> </feature-type>
          </mapping>
       </feature-map>
      <feature-content-map>

      	<mapping match="antall
      	   returnert
      	   neste/start
      	   neste/href
      	   ">
      		<attributes>
                 <attribute>
                    <name>   <matched expr="local-name"/> </name>
                    <value>  <extract expr="."/>  </value>
                 </attribute>
              </attributes>
           </mapping>

       </feature-content-map>
      </xfMap>
    XML_INPUT_TYPE = Attribute with XML document
    ATTRIBUTE_XML = _url_contents
    XML_SOURCE_NAME = _xml_source_
    MAPPED -> Tester
Tester
    TEST_MODE = Automatic
    TEST_DESCRIPTION = ""
    BOOL_OP = OR
    TEST_CLAUSE = TEST @Value(returnert) > 0
    PASSED -> Tester_Passed (output)
    PASSED -> AttributeCreator_4
    FAILED -> Tester_Failed (output)
